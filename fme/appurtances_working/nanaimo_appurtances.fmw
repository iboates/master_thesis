FME workspace nanaimo_appurtances.fmw

Parameters:
- SourceDataset_ESRISHAPE = /media/isaac/Data/EIFER/UNADE_V2/CityGML-UtilityNetwork-ADE/Sample/Nanaimo_Water_Network/v2/data_in/parcels.shp   # Source Esri Shapefile(s)
- SourceDataset_ESRISHAPE_11 = /media/isaac/Data/EIFER/UNADE_V2/CityGML-UtilityNetwork-ADE/Sample/Nanaimo_Water_Network/v2/data_in/buildings.shp   # Source Esri Shapefile(s)
- DestDataset_CITYGML = /media/isaac/Data/_GMCM/Thesis/data/citygml/nanaimo_water_network.gml   # Destination CityGML Document
- SourceDataset_GEOTIFF = /media/isaac/Data/EIFER/UNADE_V2/CityGML-UtilityNetwork-ADE/Sample/Nanaimo_Water_Network/v2/data_in/Nanaimo_DEM.tif   # Source GeoTIFF File(s)
- SourceDataset_GEOTIFF_3 = /media/isaac/Data/EIFER/UNADE_V2/CityGML-UtilityNetwork-ADE/Sample/Nanaimo_Water_Network/v2/data_in/Nanaimo_DEM.tif   # Source GeoTIFF File(s)
- SourceDataset_ESRISHAPE_8 = /media/isaac/Data/_GMCM/Thesis/data/misc/reservoir_no1_clipper.shp   # Source Esri Shapefile(s)
- SourceDataset_ESRISHAPE_10 = /media/isaac/Data/_GMCM/Thesis/data/nanaimo_open_data_portal/Water/SERVICES.shp   # Source Esri Shapefile(s)
- SourceDataset_ESRISHAPE_9 = /media/isaac/Data/_GMCM/Thesis/data/nanaimo_open_data_portal/Water/PIPES.shp   # Source Esri Shapefile(s)
- SourceDataset_ESRISHAPE_7 = /media/isaac/Data/_GMCM/Thesis/data/nanaimo_open_data_portal/Water/APPURTENANCES.shp   # Source Esri Shapefile(s)

Readers:
- ESRISHAPE_1: ESRISHAPE from $(SourceDataset_ESRISHAPE)
- ESRISHAPE_2: ESRISHAPE from $(SourceDataset_ESRISHAPE_11)
- GEOTIFF_1: GEOTIFF from $(SourceDataset_GEOTIFF)
- GEOTIFF_2: GEOTIFF from $(SourceDataset_GEOTIFF_3)
- ESRISHAPE_3: ESRISHAPE from $(SourceDataset_ESRISHAPE_8)
- ESRISHAPE_4: ESRISHAPE from $(SourceDataset_ESRISHAPE_10)
- ESRISHAPE_5: ESRISHAPE from $(SourceDataset_ESRISHAPE_9)
- ESRISHAPE_6: ESRISHAPE from $(SourceDataset_ESRISHAPE_7)

Writers:
- CITYGML_1: CITYGML to $(DestDataset_CITYGML) in EPSG:26910

APPURTENANCES (reader ESRISHAPE_6)
    attributes: TYPE char(20), WATERCATEG char(20), OWNER char(20), YEAR long, ASBUILT long, ACCURACY char(20), NODEELEVAT number(31,15), FIELDID char(10), NODEID number(11,0), GID number(11,0)
    -> SpatialFilter_5 [Candidate]
reservoir_no1_clipper (reader ESRISHAPE_3)
    attributes: id long
    -> SpatialFilter_3 [Filter]
    -> SpatialFilter_2 [Filter]
    -> SpatialFilter [Filter]
    -> SpatialFilter_4 [Filter]
    -> SpatialFilter_5 [Filter]
SpatialFilter_5
    AGGREGATE_HANDLING = Yes
    ATTR_CONFLICT_RES = Use Candidate
    BASE_TYPE = Multiple Filters
    PREDATTR = _predicate
    USE_BOUNDING_BOX = No
    CURVE_BOUNDARY_RULE_PARAM = Default Rule
    PASS_CRITERIA = Pass Against One Filter
    ATTR_ACCUM_MODE = Merge Filter
    PREDICATES = INTERSECTS
    PASSED -> FeatureMerger_11 [REQUESTOR]
Creator_3
    NUM = 1
    GEOMTYPE = Geometry Object
    CREATED -> UUIDGenerator_4
Note: Set feature role as transportedMedium. / Also set transportedMedium to be freshWater + its properties
AttributeCreator_9
    ATTR_TABLE:
      SET_TO citygml_feature_role = transportedMedium
      SET_TO utility_type = freshWater
      SET_TO utility_is_corrosive = 0
      SET_TO utility_is_explosive = 0
      SET_TO utility_flammable = 0
    -> AttributeRenamer_10
Note: Set LiquidMedium ID as gml_id / Also set NetworkID as parent_gml_id
AttributeRenamer_10
    ATTR_TABLE:
      RENAME_SET_DEFAULT LiquidMedium_ID > gml_id
      RENAME_SET_DEFAULT Network_ID > gml_parent_id
    -> LiquidMedium (writer CITYGML_1)
LiquidMedium (writer CITYGML_1)
    attributes: citygml_target_uri xml_buffer, citygml_feature_role xml_buffer, citygml_feature_role_attr_name xml_buffer, citygml_feature_role_attr_val xml_buffer, gml_description xml_buffer, gml_name xml_buffer, utility_owner xml_buffer, utility_is_classified_by{}.xlink_href xml_buffer, utility_associated_network{}.xlink_href xml_buffer, utility_type xml_buffer, utility_type_codeSpace xml_buffer, utility_is_corrosive xml_boolean, utility_is_explosive xml_boolean, utility_flammable xml_real64, utility_electric_conductivity xml_buffer, utility_electric_conductivity_units xml_buffer, utility_ph_value_range xml_buffer, utility_ph_value_range_units xml_buffer, utility_temperature_range xml_buffer, utility_temperature_range_units xml_buffer, utility_flow_rate_range xml_buffer, utility_flow_rate_range_units xml_buffer, utility_pressure_range xml_buffer, utility_pressure_range_units xml_buffer
Note: Set function & usage = distribution
AttributeCreator_5
    ATTR_TABLE:
      SET_TO utility_usage{0} = distribution
      SET_TO utility_function{0} = distribution
    -> AttributeRenamer_4
Note: Set the network ID as the gml_id / Also set the transportedMedium to be the LiquidMedium ID
AttributeRenamer_4
    ATTR_TABLE = RENAME_SET_DEFAULT Network_ID > gml_id
    -> Network (writer CITYGML_1)
Network (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_medium_supply{}.utility_electrical_medium_supply_utility_potential_supply_utility_supply_utility_flow_rate xml_real64,
      utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29), utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer,
      utility_medium_supply{}.utility_liquid_medium_supply_utility_type xml_buffer, utility_medium_supply{}.utility_liquid_medium_supply_utility_type_codeSpace xml_buffer, utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64,
      utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_role_in_network{}.xlink_href xml_buffer, citygml_appearance{}.xlink_href xml_buffer, utility_class xml_buffer, utility_class_codeSpace xml_buffer, utility_function{} xml_buffer, utility_function{}.codeSpace xml_buffer, utility_usage{} xml_buffer, utility_usage{}.codeSpace xml_buffer,
      utility_transported_medium_xlink_href xml_buffer, utility_sub_network{}.xlink_href xml_buffer, utility_topo_graph_xlink_href xml_buffer, utility_component{}.xlink_href xml_buffer, utility_supplies_xlink_href xml_buffer, utility_sub_ordinate_network{}.xlink_href xml_buffer, utility_super_ordinate_network{}.xlink_href xml_buffer
Note: Set relationship between Network / and NetworkGraph (+topoGraph)
AttributeCreator_24
    ATTR_TABLE = SET_TO citygml_feature_role = topoGraph
    -> AttributeRenamer_3
Note: Set gml_id as NetworkGraph_ID / and gml_parent_id as NetworkGraph_ID
AttributeRenamer_3
    ATTR_TABLE:
      RENAME_SET_DEFAULT NetworkGraph_ID > gml_id
      RENAME_SET_DEFAULT Network_ID > gml_parent_id
    -> NetworkGraph (writer CITYGML_1)
NetworkGraph (writer CITYGML_1)
    attributes: citygml_target_uri xml_buffer, citygml_feature_role xml_buffer, citygml_feature_role_attr_name xml_buffer, citygml_feature_role_attr_val xml_buffer, gml_description xml_buffer, gml_name xml_buffer, utility_feature_graph_member{}.xlink_href xml_buffer, utility_link_member{}.xlink_href xml_buffer
FeatureMerger_11
    ATTR_CONFLICT_RES = Use Requestor
    IGNORE_NULLS = No
    PROCESS_DUPS = No
    MERGE_TYPE = Attributes Only
    REJECT_NULL_MISSING_KEYS = No
    JOIN_KEYS = 1 1 AUTO
    SUPPLIERS_FIRST = No
    ATTR_ACCUM_MODE = Merge Supplier
    MERGED -> AttributeFilter_4
AttributeRemover_2
    REMOVE_ATTRS = GID,WATERCATEG,NetworkGraph_ID,NODEELEVAT,Junction_ID,id,YEAR,TYPE,Network_ID,NODEID,OWNER
    -> PointOnLineOverlayer_3 [POINT]
AttributeRemover_4
    REMOVE_ATTRS = NetworkGraph_ID,citygml_lod_name,_predicate,ASBUILT,TYPE,WATERCATEG,id,Network_ID,ACCURACY,OWNER,FeatureGraph_ID,FIELDID,NODEID,YEAR,GID,NODEELEVAT,Junction_ID,_creation_instance
    -> PointOnPointOverlayer [POINT]
PIPES (reader ESRISHAPE_5)
    attributes: TYPE char(20), DIAMETER number(11,0), MATERIAL char(20), WATERCATEG char(20), CATCHMENT char(50), OWNER char(20), YEAR long, ASBUILT long, ACCURACY char(20), LENGTH float, STARTID number(11,0), ENDID number(11,0), PIPEID number(11,0), GID number(11,0)
    -> SpatialFilter_3 [Candidate]
SpatialFilter_3
    AGGREGATE_HANDLING = Yes
    ATTR_CONFLICT_RES = Use Candidate
    BASE_TYPE = Multiple Filters
    PREDATTR = _predicate
    USE_BOUNDING_BOX = No
    CURVE_BOUNDARY_RULE_PARAM = Default Rule
    PASS_CRITERIA = Pass Against One Filter
    ATTR_ACCUM_MODE = Merge Filter
    PREDICATES = INTERSECTS
    PASSED -> FeatureHolder_2
    PASSED -> SpatialRelator [Supplier]
SERVICES (reader ESRISHAPE_4)
    attributes: DIAMETER long, MATERIAL char(20), WATERCATEG char(20), OWNER char(20), YEAR long, ASBUILT number(11,0), ACCURACY char(20), LENGTH float, PIPEID number(11,0), PARCELGID number(11,0), STARTDEPTH float, ENDDEPTH float, GID number(11,0)
    -> SpatialFilter_2 [Candidate]
SpatialFilter_2
    AGGREGATE_HANDLING = Yes
    ATTR_CONFLICT_RES = Use Candidate
    BASE_TYPE = Multiple Filters
    PREDATTR = _predicate
    USE_BOUNDING_BOX = No
    CURVE_BOUNDARY_RULE_PARAM = Default Rule
    PASS_CRITERIA = Pass Against One Filter
    ATTR_ACCUM_MODE = Merge Filter
    PREDICATES = INTERSECTS
    PASSED -> SpatialRelator_2 [Supplier]
    PASSED -> SpatialRelator_2 [Requestor]
    PASSED -> SpatialRelator [Requestor]
FeatureHolder_2
    -> PointOnLineOverlayer_3 [LINE]
Note: split the feature graph lines with the / appurtenance points
PointOnLineOverlayer_3
    ATTR_CONFLICT_RES = Use Original
    DEAGGREGATE_INPUT = Yes
    ATTR_ACCUM_MODE = Merge Incoming
    OV_ATTR = _overlaps
    TOLERANCE = 0.1
    POINT -> PointOnLineOverlayer_3_Point
    LINE -> UUIDGenerator_12
    LINE -> PointOnLineOverlayer_3_Line
FeatureMerger_9
    ATTR_CONFLICT_RES = Use Requestor
    IGNORE_NULLS = No
    PROCESS_DUPS = No
    MERGE_TYPE = Attributes Only
    REJECT_NULL_MISSING_KEYS = No
    JOIN_KEYS = 1 1 AUTO
    SUPPLIERS_FIRST = No
    ATTR_ACCUM_MODE = Merge Supplier
    MERGED -> GeometryRemover_5
    MERGED -> SurfaceDraper [DRAPE_FEATURES]
    MERGED -> DuplicateFilter_2
    MERGED -> AttributeRenamer
    MERGED -> PointOnLineOverlayer_2 [LINE]
PointOnLineOverlayer_2
    ATTR_CONFLICT_RES = Use Original
    DEAGGREGATE_INPUT = Yes
    ATTR_ACCUM_MODE = Merge Incoming
    OV_ATTR = _overlaps
    TOLERANCE = 0.1
    LINE -> AttributeRemover
Note: Have to delete al the attributes created by the / old TopologyBuilder, otherwise it makes the / Node/InteriorFeatureLink logic fail layer
AttributeRemover
    REMOVE_ATTRS = _node_angle{0}._edge_id,_node_angle{0}.PIPEID,_node_angle{0}.ServiceLine_ID,_faces{0}.MATERIAL,_faces{0}.WATERCATEG,_node_angle{0}.STARTDEPTH,_faces{0}.PARCELGID,_faces{0}._creation_instance,_faces{0}.LENGTH,_node_angle{0}._creation_instance,_faces{0}.ServiceLine_ID,_faces{0}.ENDDEPTH,_faces{0}.YEAR,_node_angle{0}.WATERCATEG,_node_angle{0}.LENGTH,_faces{0}.PIPEID,_node_angle{0}.ASBUILT,_node_angle{0}.YEAR,_node_angle{0}.fme_arc_angle,_faces{0}._face_id,_faces{0}.ACCURACY,_faces{0}.ASBUILT,_node_angle{0}.fme_arc_id,_node_angle{0}.OWNER,_faces{0}.STARTDEPTH,_node_angle{0}.fme_direction,_node_angle{0}.GID,_faces{0}.DIAMETER,_node_angle{0}.MATERIAL,_node_angle{0}.PARCELGID,_faces{0}._predicate,_faces{0}._related_candidates,_node_angle{0}._predicate,_node_angle{0}.ACCURACY,_node_angle{0}.DIAMETER,_faces{0}.GID,_node_angle{0}._related_candidates,_node_angle{0}.ENDDEPTH,_faces{0}.OWNER,_related_candidates,_node_number,_overlaps
    -> TopologyBuilder_2
TopologyBuilder_2
    ALLOW_CYCLES = No
    MAX = 0
    PROP_ATTRS = Yes
    BOUNDING_EDGES = All
    CLEAN_DATA = Yes
    OVERLAPPING_MODE = No
    DEAGGREGATE_INPUT = Yes
    NODE -> ListExploder
    LINE -> UUIDGenerator_18
Note: 1. Each node contains a list which lists all lines (i.e. the corresponding arc_ids) that are connected with the node. / This list is split up here so that each node is connected to one line only. / The number of nodes duplicates analogously to the number of lines connected with a node.
ListExploder
    LIST_ATTR = _node_angle{}
    ATTR_ACCUM_MODE = Merge Incoming List
    INDEX_ATTR = _element_index
    ATTR_CONFLICT_RES = Use Incoming List
    ELEMENTS -> ExpressionEvaluator
Note: Arc_ids with a negative sign are / turned into positive numbers here.
ExpressionEvaluator
    ATTRLIST = fme_arc_id
    ACTION = Overwrite Existing Attributes
    EXPRESSION = @abs(@Value(fme_arc_id))
    -> UUIDGenerator_11
Note: Set relationship between FeatureGraph / and InteriorFeatureLink (+linkMember)
AttributeCreator_6
    ATTR_TABLE = SET_TO citygml_feature_role = linkMember
    -> AttributeRenamer_9
Note: Set gml_id (InteriorFeatureLink ID) / Also set gml_parent_id (FeatureGraph)
AttributeRenamer_9
    ATTR_TABLE:
      RENAME_SET_DEFAULT InteriorFeatureLink_ID > gml_id
      RENAME_SET_DEFAULT FeatureGraph_ID > gml_parent_id
    -> StringConcatenator_19
    -> interiorfeaturelink
interiorfeaturelink: Inspector [off]
StringConcatenator_19
    PARM_LINE = #@Value(utility_end_xlink_href)
    ATTRLIST = utility_end_xlink_href
    ACTION = Overwrite Existing Attributes
    -> StringConcatenator_27
StringConcatenator_27
    PARM_LINE = #@Value(utility_start_xlink_href)
    ATTRLIST = utility_start_xlink_href
    ACTION = Overwrite Existing Attributes
    -> InteriorFeatureLink (writer CITYGML_1)
InteriorFeatureLink (writer CITYGML_1)
    attributes: citygml_target_uri xml_buffer, citygml_feature_role xml_buffer, citygml_feature_role_attr_name xml_buffer, citygml_feature_role_attr_val xml_buffer, gml_description xml_buffer, gml_name xml_buffer, utility_direction xml_char(1), utility_link_control xml_xml, utility_start_xlink_href xml_buffer, utility_end_xlink_href xml_buffer
FeatureMerger_5
    ATTR_CONFLICT_RES = Use Requestor
    IGNORE_NULLS = No
    PROCESS_DUPS = No
    MERGE_TYPE = Attributes Only
    REJECT_NULL_MISSING_KEYS = No
    JOIN_KEYS = @Value(Node_ID) @Value(utility_start_xlink_href) AUTO
    SUPPLIERS_FIRST = No
    ATTR_ACCUM_MODE = Merge Supplier
    MERGED -> AttributeCreator_11
    NOT_MERGED -> FeatureMerger_6 [REQUESTOR]
FeatureMerger_6
    ATTR_CONFLICT_RES = Use Requestor
    IGNORE_NULLS = No
    PROCESS_DUPS = No
    MERGE_TYPE = Attributes Only
    REJECT_NULL_MISSING_KEYS = No
    JOIN_KEYS = @Value(Node_ID) @Value(utility_end_xlink_href) AUTO
    SUPPLIERS_FIRST = No
    ATTR_ACCUM_MODE = Merge Supplier
    MERGED -> AttributeCreator_11
Note: Set type = exterior
AttributeCreator_11
    ATTR_TABLE = SET_TO utility_type = exterior
    -> AttributeRemover_3
    -> UUIDGenerator_22
Note: Set relation between FeatureGraph / and Node (+nodeMember)
AttributeCreator_8
    ATTR_TABLE = SET_TO citygml_feature_role = nodeMember
    -> AttributeRenamer_14
    -> AttributeFilter_5
Note: Set gml_id to Node_ID / and gml_parent_id to FeatureGraph_ID
AttributeRenamer_14
    ATTR_TABLE:
      RENAME_SET_DEFAULT Node_ID > gml_id
      RENAME_SET_DEFAULT FeatureGraph_ID > gml_parent_id
    -> Node (writer CITYGML_1)
    -> nodes
nodes: Inspector [off]
AttributeFilter_5
    ATTR_NAME = Junction_Node_ID
    ATTR_VALUES = <Empty>,<Missing>,<Null>,<Unfiltered>
    <UNFILTERED> -> AttributeRenamer_30
AttributeRenamer_30
    ATTR_LIST = Node_ID,utility_start_xlink_href,,Junction_Node_ID,utility_end_xlink_href,
    -> StringConcatenator_30
StringConcatenator_30
    PARM_LINE = #@Value(utility_start_xlink_href)
    ATTRLIST = utility_start_xlink_href
    ACTION = Overwrite Existing Attributes
    -> StringConcatenator_31
StringConcatenator_31
    PARM_LINE = #@Value(utility_end_xlink_href)
    ATTRLIST = utility_end_xlink_href
    ACTION = Overwrite Existing Attributes
    -> GeometryRemover_4
GeometryRemover_4
    -> AttributeCreator_44
Note: Set utility_type = connects
AttributeCreator_44
    ATTR_TABLE = SET_TO utility_type = connects
    -> AttributeCreator_43
Note: Set relationship between InterFeatureLink / and NetworkGraph (+linkMember)
AttributeCreator_43
    ATTR_LIST = citygml_feature_role,linkMember
    -> AttributeRenamer_31
Note: Set gml_id to InterFeatureLink_ID / and gml_parent_id to NetworkGraph_ID
AttributeRenamer_31
    ATTR_LIST = InterFeatureLink_ID,gml_id,,NetworkGraph_ID,gml_parent_id,
    -> InterFeatureLink (writer CITYGML_1)
AttributeRemover_3
    REMOVE_ATTRS = _faces{0}._faces{0}.LENGTH,_nodes{0}._node_angle{0}.MATERIAL,utility_start_xlink_href,_nodes{0}._faces{0}.DIAMETER,_faces{0}._faces{0}.PIPEID,_node_angle{0}.DIAMETER,_nodes{0}._node_angle{0}.ServiceLine_ID,_faces{0}._node_angle{0}.fme_arc_id,_nodes{0}._node_angle{0}.PARCELGID,_nodes{0}._node_angle{0}.fme_arc_id,ENDDEPTH,_creation_instance,Junction_Node_ID,_nodes{0}.CATCHMENT,_faces{0}._node_angle{0}.YEAR,_nodes{0}._node_angle{0}.ACCURACY,_node_angle{0}.fme_arc_id,_nodes{0}.STARTID,_to_node,FIELDID,_node_angle{0}.WATERCATEG,id,_nodes{0}._faces{0}.WATERCATEG,fme_arc_angle,_nodes{0}.ACCURACY,_faces{0}.MATERIAL,_faces{0}._node_angle{0}.ENDDEPTH,_node_angle{0}.ENDDEPTH,_faces{0}.PARCELGID,_nodes{0}._faces{0}.ENDDEPTH,_faces{0}._faces{0}.ACCURACY,_nodes{0}.id,_faces{0}.STARTDEPTH,_nodes{0}._faces{0}.GID,TYPE,STARTDEPTH,_nodes{0}._node_angle{0}.fme_direction,_faces{0}.ENDDEPTH,_nodes{0}._node_angle{0}.ASBUILT,DIAMETER,citygml_lod_name,_faces{0}.id,_faces{0}.ASBUILT,_nodes{0}._node_angle{0}.DIAMETER,_node_angle{0}.PARCELGID,_nodes{0}.Network_ID,STARTID,_nodes{0}.LENGTH,_faces{0}._node_angle{0}.OWNER,_faces{0}._related_candidates,_nodes{0}.citygml_lod_name,_faces{0}.STARTID,_nodes{0}.YEAR,_faces{0}._node_angle{0}.GID,_faces{0}._face_id,ServiceLine_ID,on_pipe,_nodes{0}.ASBUILT,_faces{0}._faces{0}._face_id,_from_node,_nodes{0}.FIELDID,_nodes{0}._node_angle{0}.ENDDEPTH,_nodes{0}.MATERIAL,LENGTH,_node_number,MATERIAL,_nodes{0}.Junction_Node_ID,_faces{0}._faces{0}.ASBUILT,_faces{0}.PIPEID,_faces{0}._faces{0}.MATERIAL,_faces{0}._node_angle{0}.WATERCATEG,_faces{0}.NetworkGraph_ID,_node_angle{0}.ServiceLine_ID,_nodes{0}._faces{0}.ACCURACY,FeatureGraph_ID,_nodes{0}._node_angle{0}.fme_arc_angle,_faces{0}._node_angle{0}._related_candidates,_faces{0}._predicate,_nodes{0}.Parent_RoundPipe_ID,_node_angle{0}._related_candidates,_nodes{0}.ServiceLine_ID,fme_direction,WATERCATEG,_nodes{0}._node_angle{0}._related_candidates,_node_angle{0}.ASBUILT,_faces{0}._node_angle{0}._edge_id,_faces{0}._node_angle{0}.ACCURACY,_faces{0}.fme_direction,_nodes{0}._faces{0}._predicate,_faces{0}.citygml_lod_name,_node_angle{0}.PIPEID,_faces{0}.ServiceLine_ID,_faces{0}.FeatureGraph_ID,_faces{0}._faces{0}.WATERCATEG,_nodes{0}._node_angle{0}._predicate,_faces{0}.RoundPipe_ID,_faces{0}._node_angle{0}.ASBUILT,_faces{0}._node_angle{0}.PARCELGID,utility_end_xlink_href,_node_angle{0}.GID,_node_angle{0}.MATERIAL,_nodes{0}._faces{0}.ServiceLine_ID,_faces{0}.YEAR,_faces{0}._node_angle{0}.PIPEID,_nodes{0}._node_angle{0}.LENGTH,_nodes{0}.GID,_edge_id,_faces{0}._node_angle{0}.LENGTH,_faces{0}.ACCURACY,_faces{0}._faces{0}.id,_nodes{0}.PARCELGID,_faces{0}.DIAMETER,_node_angle{0}._predicate,_nodes{0}._node_angle{0}.YEAR,_faces{0}.OWNER,_nodes{0}.on_pipe,PARCELGID,YEAR,ACCURACY,_nodes{0}.OWNER,_faces{0}._node_angle{0}.fme_arc_angle,_nodes{0}._faces{0}.PIPEID,OWNER,_faces{0}._faces{0}.PARCELGID,_element_index,_node_angle{0}.ACCURACY,_faces{0}._faces{0}.GID,_nodes{0}._faces{0}._related_candidates,_faces{0}._node_angle{0}.STARTDEPTH,_nodes{0}.STARTDEPTH,_nodes{0}._faces{0}.ASBUILT,_nodes{0}._faces{0}.LENGTH,_nodes{0}.TYPE,_faces{0}.TYPE,_faces{0}._faces{0}.STARTDEPTH,_nodes{0}._node_angle{0}.PIPEID,_faces{0}.CATCHMENT,_faces{0}._node_angle{0}.MATERIAL,_node_angle{0}.OWNER,Parent_RoundPipe_ID,_faces,InteriorFeatureLink_ID,_left_face,_nodes{0}.PIPEID,_faces{0}._faces{0}.OWNER,_nodes{0}.DIAMETER,_node_angle{0}.id,_faces{0}._creation_instance,_node_angle{0}.LENGTH,_faces{0}._faces{0}._predicate,_nodes{0}._node_angle{0}.GID,_nodes{0}._node_angle{0}.OWNER,_node_angle{0}.fme_arc_angle,_nodes{0}._node_angle{0}.WATERCATEG,ASBUILT,_faces{0}._node_angle{0}.DIAMETER,_faces{0}.LENGTH,_related_candidates,utility_type,_node_angle{0}.STARTDEPTH,_nodes{0}._faces{0}.OWNER,GID,_faces{0}.GID,_faces{0}.Junction_Node_ID,ENDID,_nodes{0}._faces{0}._face_id,_nodes{0}._node_number,fme_arc_id,PIPEID,_nodes{0}._faces{0}.YEAR,_faces{0}._faces{0}.ServiceLine_ID,_nodes{0}._node_angle{0}._edge_id,_nodes{0}.ENDID,_left_edge,_predicate,_nodes{0}.ENDDEPTH,_nodes{0}.WATERCATEG,_nodes{0}.RoundPipe_ID,_nodes{0}.NetworkGraph_ID,_nodes{0}._creation_instance,Network_ID,_faces{0}.FIELDID,_faces{0}._node_angle{0}.ServiceLine_ID,_nodes{0}.FeatureGraph_ID,_faces{0}._node_angle{0}._predicate,CATCHMENT,_faces{0}._faces{0}.ENDDEPTH,_right_edge,_faces{0}._faces{0}.YEAR,_nodes{0}._predicate,_faces{0}._node_angle{0}.id,_faces{0}._faces{0}._related_candidates,_nodes{0}._node_angle{0}.STARTDEPTH,_nodes{0}._faces{0}.STARTDEPTH,_faces{0}.Parent_RoundPipe_ID,_nodes{0}._faces{0}.id,RoundPipe_ID,_faces{0}._faces{0}.DIAMETER,_nodes{0}._faces{0}.PARCELGID,_nodes{0}._node_angle{0}.id,_faces{0}._node_angle{0}.fme_direction,_right_face,_faces{0}.ENDID,_faces{0}.WATERCATEG,_nodes{0}._faces{0}.MATERIAL,_node_angle{0}.fme_direction,_node_angle{0}.YEAR,_faces{0}.Network_ID,_faces{0}.on_pipe
    LIST_ATTRS = _faces{} _faces{}.ACCURACY _faces{}.ASBUILT _faces{}.CATCHMENT _faces{}.DIAMETER _faces{}.ENDDEPTH _faces{}.ENDID _faces{}.FIELDID _faces{}.FeatureGraph_ID _faces{}.GID _faces{}.Junction_Node_ID _faces{}.LENGTH _faces{}.MATERIAL _faces{}.NetworkGraph_ID _faces{}.Network_ID _faces{}.OWNER _faces{}.PARCELGID _faces{}.PIPEID _faces{}.Parent_RoundPipe_ID _faces{}.RoundPipe_ID _faces{}.STARTDEPTH _faces{}.STARTID _faces{}.ServiceLine_ID _faces{}.TYPE _faces{}.WATERCATEG _faces{}.YEAR _faces{}._creation_instance _faces{}._face_id _faces{}._faces{} _faces{}._faces{}.ACCURACY _faces{}._faces{}.ASBUILT _faces{}._faces{}.DIAMETER _faces{}._faces{}.ENDDEPTH _faces{}._faces{}.GID _faces{}._faces{}.LENGTH _faces{}._faces{}.MATERIAL _faces{}._faces{}.OWNER _faces{}._faces{}.PARCELGID _faces{}._faces{}.PIPEID _faces{}._faces{}.STARTDEPTH _faces{}._faces{}.ServiceLine_ID _faces{}._faces{}.WATERCATEG _faces{}._faces{}.YEAR _faces{}._faces{}._face_id _faces{}._faces{}._predicate _faces{}._faces{}._related_candidates _faces{}._faces{}.id _faces{}._node_angle{} _faces{}._node_angle{}.ACCURACY _faces{}._node_angle{}.ASBUILT _faces{}._node_angle{}.DIAMETER _faces{}._node_angle{}.ENDDEPTH _faces{}._node_angle{}.GID _faces{}._node_angle{}.LENGTH _faces{}._node_angle{}.MATERIAL _faces{}._node_angle{}.OWNER _faces{}._node_angle{}.PARCELGID _faces{}._node_angle{}.PIPEID _faces{}._node_angle{}.STARTDEPTH _faces{}._node_angle{}.ServiceLine_ID _faces{}._node_angle{}.WATERCATEG _faces{}._node_angle{}.YEAR _faces{}._node_angle{}._edge_id _faces{}._node_angle{}._predicate _faces{}._node_angle{}._related_candidates _faces{}._node_angle{}.fme_arc_angle _faces{}._node_angle{}.fme_arc_id _faces{}._node_angle{}.fme_direction _faces{}._node_angle{}.id _faces{}._predicate _faces{}._related_candidates _faces{}.citygml_lod_name _faces{}.fme_direction _faces{}.id _faces{}.on_pipe _node_angle{} _node_angle{}.ACCURACY _node_angle{}.ASBUILT _node_angle{}.DIAMETER _node_angle{}.ENDDEPTH _node_angle{}.GID _node_angle{}.LENGTH _node_angle{}.MATERIAL _node_angle{}.OWNER _node_angle{}.PARCELGID _node_angle{}.PIPEID _node_angle{}.STARTDEPTH _node_angle{}.ServiceLine_ID _node_angle{}.WATERCATEG _node_angle{}.YEAR _node_angle{}._edge_id _node_angle{}._predicate _node_angle{}._related_candidates _node_angle{}.fme_arc_angle _node_angle{}.fme_arc_id _node_angle{}.fme_direction _node_angle{}.id _nodes{} _nodes{}.ACCURACY _nodes{}.ASBUILT _nodes{}.CATCHMENT _nodes{}.DIAMETER _nodes{}.ENDDEPTH _nodes{}.ENDID _nodes{}.FIELDID _nodes{}.FeatureGraph_ID _nodes{}.GID _nodes{}.Junction_Node_ID _nodes{}.LENGTH _nodes{}.MATERIAL _nodes{}.NetworkGraph_ID _nodes{}.Network_ID _nodes{}.OWNER _nodes{}.PARCELGID _nodes{}.PIPEID _nodes{}.Parent_RoundPipe_ID _nodes{}.RoundPipe_ID _nodes{}.STARTDEPTH _nodes{}.STARTID _nodes{}.ServiceLine_ID _nodes{}.TYPE _nodes{}.WATERCATEG _nodes{}.YEAR _nodes{}._creation_instance _nodes{}._faces{} _nodes{}._faces{}.ACCURACY _nodes{}._faces{}.ASBUILT _nodes{}._faces{}.DIAMETER _nodes{}._faces{}.ENDDEPTH _nodes{}._faces{}.GID _nodes{}._faces{}.LENGTH _nodes{}._faces{}.MATERIAL _nodes{}._faces{}.OWNER _nodes{}._faces{}.PARCELGID _nodes{}._faces{}.PIPEID _nodes{}._faces{}.STARTDEPTH _nodes{}._faces{}.ServiceLine_ID _nodes{}._faces{}.WATERCATEG _nodes{}._faces{}.YEAR _nodes{}._faces{}._face_id _nodes{}._faces{}._predicate _nodes{}._faces{}._related_candidates _nodes{}._faces{}.id _nodes{}._node_angle{} _nodes{}._node_angle{}.ACCURACY _nodes{}._node_angle{}.ASBUILT _nodes{}._node_angle{}.DIAMETER _nodes{}._node_angle{}.ENDDEPTH _nodes{}._node_angle{}.GID _nodes{}._node_angle{}.LENGTH _nodes{}._node_angle{}.MATERIAL _nodes{}._node_angle{}.OWNER _nodes{}._node_angle{}.PARCELGID _nodes{}._node_angle{}.PIPEID _nodes{}._node_angle{}.STARTDEPTH _nodes{}._node_angle{}.ServiceLine_ID _nodes{}._node_angle{}.WATERCATEG _nodes{}._node_angle{}.YEAR _nodes{}._node_angle{}._edge_id _nodes{}._node_angle{}._predicate _nodes{}._node_angle{}._related_candidates _nodes{}._node_angle{}.fme_arc_angle _nodes{}._node_angle{}.fme_arc_id _nodes{}._node_angle{}.fme_direction _nodes{}._node_angle{}.id _nodes{}._node_number _nodes{}._predicate _nodes{}.citygml_lod_name _nodes{}.id _nodes{}.on_pipe
    -> PointOnPointOverlayer [POINT]
Note: Overlay the nodes with the junction nodes
PointOnPointOverlayer
    LIST_ATTRS_TO_INCLUDE = Node_ID
    OV_ATTR = _overlaps
    ATTR_ACCUM_MODE = Merge Incoming
    TOLERANCE = 0.01
    LIST_NAME = Non_Junction_Node_IDs
    DEAGGREGATE_INPUT = Yes
    ATTR_CONFLICT_RES = Use Original
    POINT -> ListExploder_2
ListExploder_2
    LIST_ATTR = Non_Junction_Node_IDs{}
    ATTR_ACCUM_MODE = Merge List Attributes
    INDEX_ATTR = Non_Junction_Node_ID_index
    ATTR_CONFLICT_RES = Use List Attribute Values
    ELEMENTS -> AttributeFilter_6
AttributeFilter_6
    ATTR_NAME = Junction_Node_ID
    ATTR_VALUES = <Empty>,<Missing>,<Null>,<Unfiltered>
    <UNFILTERED> -> UUIDGenerator_21
AttributeCreator_46
    ATTR_TABLE:
      SET_TO citygml_feature_role = linkMember
      SET_TO utility_type = connects
    -> AttributeRenamer_33
AttributeRenamer_33
    ATTR_LIST = Junction_Node_ID,utility_start_xlink_href,,Node_ID,utility_end_xlink_href,,InterFeatureLink_ID,gml_id,,NetworkGraph_ID,gml_parent_id,
    -> StringConcatenator_34
StringConcatenator_34
    PARM_LINE = #@Value(utility_start_xlink_href)
    ATTRLIST = utility_start_xlink_href
    ACTION = Overwrite Existing Attributes
    -> StringConcatenator_35
StringConcatenator_35
    PARM_LINE = #@Value(utility_end_xlink_href)
    ATTRLIST = utility_end_xlink_href
    ACTION = Overwrite Existing Attributes
    -> GeometryRemover_6
GeometryRemover_6
    -> InterFeatureLink (writer CITYGML_1)
AttributeRenamer_17
    ATTR_TABLE = RENAME_SET_DEFAULT Node_ID > Service_Node_ID
    -> SpatialRelator_5 [Supplier]
inspector1_2: Inspector [off]
Note: Make list of unique MATERIAL values / from source data
DuplicateFilter_2
    KEYATTR = MATERIAL
    INPUT_ORDERED_CHOICE = No
    UNIQUE -> AttributeValueMapper_5
Note: material values - lots of unknowns
AttributeValueMapper_5
    SRC = MATERIAL
    LUT = AC,concrete,CI,iron,CP,unknown,CU,copper,DI,iron,HDPE,PE,PE,PE,PS,unknown,PVC,PVC,ST,unknown,UN,unknown,Unknown,unknown
    DEFAULT_VALUE = unknown
    VAL_ATTR = utility_type
    DIRECTION = Forward (Source To Destination)
    -> UUIDGenerator_10
Note: Set gml_id as ExteriorMaterialID
AttributeRenamer_12
    ATTR_TABLE = RENAME_SET_DEFAULT ExteriorMaterial_ID > gml_id
    -> ExteriorMaterial (writer CITYGML_1)
ExteriorMaterial (writer CITYGML_1)
    attributes: citygml_target_uri xml_buffer, citygml_feature_role xml_buffer, citygml_feature_role_attr_name xml_buffer, citygml_feature_role_attr_val xml_buffer, gml_description xml_buffer, gml_name xml_buffer, utility_type xml_buffer, utility_type_codeSpace xml_buffer, utility_consists_of_fm{}.xlink_href xml_buffer, utility_consists_of{}.xlink_href xml_buffer, utility_is_classified_by{}.xlink_href xml_buffer, utility_used_by{}.xlink_href xml_buffer
Note: Remove Geometry because it is / irrelevant for FeatureGraphs
GeometryRemover_5
    -> AttributeCreator_4
Note: Set relationship between FeatureGraph / and NetworkGraph (+featureGraphMember)
AttributeCreator_4
    ATTR_TABLE = SET_TO citygml_feature_role = featureGraphMember
    -> AttributeRenamer_6
Note: Set gml_id (FeatureGraph_ID) / and gml_parent_id (NetworkGraph_ID)
AttributeRenamer_6
    ATTR_TABLE:
      RENAME_SET_DEFAULT FeatureGraph_ID > gml_id
      RENAME_SET_DEFAULT NetworkGraph_ID > gml_parent_id
    -> FeatureMerger_15 [SUPPLIER]
    -> AttributeCreator_35
PointOnLineOverlayer_3_Point: Inspector
PointOnLineOverlayer_3_Line: Inspector
parcels (reader ESRISHAPE_1)
    attributes: TYPE char(20), HOUSENUMBE char(20), STREETNAME char(50), POSTALCODE char(10), ACCURACY char(25), STATUS char(10), AREA number(31,15), PLAN char(20), PID char(20), GISLINK char(20), GID number(11,0), ZONING1 char(30), ZONE1_DESC char(100), ZONING2 char(30), ZONE2_DESC char(100), ZONING3 char(30), ZONE3_DESC char(100), ZONING4 char(30), ZONE4_DESC char(100)
    -> SpatialFilter [Candidate]
SpatialFilter
    AGGREGATE_HANDLING = Yes
    ATTR_CONFLICT_RES = Use Candidate
    BASE_TYPE = Multiple Filters
    PREDATTR = _predicate
    USE_BOUNDING_BOX = No
    CURVE_BOUNDARY_RULE_PARAM = Default Rule
    PASS_CRITERIA = Pass Against One Filter
    ATTR_ACCUM_MODE = Merge Filter
    PREDICATES = INTERSECTS
    PASSED -> AttributeFilter
CoordinateExtractor_2
    Z_ATTR = _z
    Y_ATTR = pipe_y
    Z_DEFAULT = 0
    MODE = Specify Coordinate
    IND = 0
    X_ATTR = pipe_x
    -> SpatialRelator_5 [Requestor]
SpatialRelator_5
    AGGREGATE_HANDLING = Yes
    ATTR_CONFLICT_RES = Use Requestor
    CALC_CARD = No
    CURVE_BOUNDARY_RULE_PARAM = Default Rule
    ATTR_ACCUM_MODE = Merge Supplier
    PREDICATES = INTERSECTS
    SUCCESS_ATTR = _related_candidates
    -> FeatureMerger_8 [SUPPLIER]
parcels: Inspector [off]
buildings (reader ESRISHAPE_2)
    attributes: TYPE char(20), FLOORS number(11,0), HEIGHT number(31,15), BASEELEVAT number(31,15), ACCURACY char(20), AREA number(31,15), GID number(11,0)
    -> SpatialFilter_4 [Candidate]
Node (writer CITYGML_1)
    attributes: citygml_target_uri xml_buffer, citygml_feature_role xml_buffer, citygml_feature_role_attr_name xml_buffer, citygml_feature_role_attr_val xml_buffer, gml_description xml_buffer, gml_name xml_buffer, utility_type xml_char(8), utility_connection_signature xml_xml, utility_link_control xml_xml
FeatureGraph (writer CITYGML_1)
    attributes: citygml_target_uri xml_buffer, citygml_feature_role xml_buffer, citygml_feature_role_attr_name xml_buffer, citygml_feature_role_attr_val xml_buffer, gml_description xml_buffer, gml_name xml_buffer, utility_link_member{}.xlink_href xml_buffer, utility_node_member{}.xlink_href xml_buffer, utility_network_link_member{}.xlink_href xml_buffer
2DForcer
    2D -> AttributeRenamer_16
AttributeRenamer_16
    ATTR_TABLE = RENAME_SET_DEFAULT Node_ID > Terminal_Node_ID
    -> FeatureMerger_8 [REQUESTOR]
FeatureMerger_8
    ATTR_CONFLICT_RES = Use Requestor
    IGNORE_NULLS = No
    PROCESS_DUPS = No
    MERGE_TYPE = Attributes Only
    REJECT_NULL_MISSING_KEYS = No
    JOIN_KEYS = @Value(Parcel_ID) @Value(Parent_ParcelID) AUTO
    SUPPLIERS_FIRST = No
    ATTR_ACCUM_MODE = Merge Supplier
    MERGED -> VertexCreator
VertexCreator
    MODE_NAME = Add Point
    XVAL = @Value(pipe_x)
    YVAL = @Value(pipe_y)
    -> UUIDGenerator_8
AttributeCreator_14
    ATTR_TABLE:
      SET_TO citygml_feature_role = linkMember
      SET_TO utility_type = connects
    -> AttributeRenamer_20
AttributeRenamer_20
    ATTR_LIST = Service_Node_ID,utility_start_xlink_href,,Terminal_Node_ID,utility_end_xlink_href,,InterFeatureLink_ID,gml_id,,NetworkGraph_ID,gml_parent_id,
    -> terminalelement_interfeaturelinks
    -> StringConcatenator_23
terminalelement_interfeaturelinks: Inspector [off]
StringConcatenator_23
    PARM_LINE = #@Value(utility_start_xlink_href)
    ATTRLIST = utility_start_xlink_href
    ACTION = Overwrite Existing Attributes
    -> StringConcatenator_24
StringConcatenator_24
    PARM_LINE = #@Value(utility_end_xlink_href)
    ATTRLIST = utility_end_xlink_href
    ACTION = Overwrite Existing Attributes
    -> AttributeCreator_36
InterFeatureLink (writer CITYGML_1)
    attributes: citygml_target_uri xml_buffer, citygml_feature_role xml_buffer, citygml_feature_role_attr_name xml_buffer, citygml_feature_role_attr_val xml_buffer, gml_description xml_buffer, gml_name xml_buffer, utility_direction xml_char(1), utility_link_control xml_xml, utility_start_xlink_href xml_buffer, utility_end_xlink_href xml_buffer, utility_type xml_char(8)
Note: Set relationship between RoundPipe / and Network (+component)
AttributeCreator
    ATTR_TABLE = SET_TO citygml_feature_role = component
    -> AttributeRenamer_5
Note: Set gml_id as RoundPipeID / and gml_parent_id as NetworkID
AttributeRenamer_5
    ATTR_TABLE:
      RENAME_SET_DEFAULT Network_ID > gml_parent_id
      RENAME_SET_DEFAULT RoundPipe_ID > gml_id
    -> FeatureMerger_7 [REQUESTOR]
Note: Map the ExteriorMaterial to the / RoundPipes
FeatureMerger_7
    ATTR_CONFLICT_RES = Use Requestor
    IGNORE_NULLS = No
    PROCESS_DUPS = No
    MERGE_TYPE = Attributes Only
    REJECT_NULL_MISSING_KEYS = No
    JOIN_KEYS = @Value(MATERIAL) @Value(MATERIAL) AUTO
    SUPPLIERS_FIRST = No
    ATTR_ACCUM_MODE = Merge Supplier
    MERGED -> AttributeRenamer_11
Note: Set relationship between RoundPipes / and ExteriorMaterials via Xlink
AttributeRenamer_11
    ATTR_TABLE = RENAME_SET_DEFAULT ExteriorMaterial_ID > utility_has_material{0}.xlink_href
    -> StringConcatenator_20
StringConcatenator_20
    PARM_LINE = #@Value(utility_has_material{0}.xlink_href)
    ATTRLIST = utility_has_material{0}.xlink_href
    ACTION = Overwrite Existing Attributes
    -> FeatureMerger_15 [REQUESTOR]
RoundPipe (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_medium_supply{}.utility_electrical_medium_supply_utility_potential_supply_utility_supply_utility_flow_rate xml_real64,
      utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29), utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer,
      utility_medium_supply{}.utility_liquid_medium_supply_utility_type xml_buffer, utility_medium_supply{}.utility_liquid_medium_supply_utility_type_codeSpace xml_buffer, utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64,
      utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer, utility_function_of_line xml_buffer, utility_function_of_line_codeSpace xml_buffer, utility_is_gravity xml_boolean, utility_exterior_width xml_real64, utility_exterior_width_units xml_buffer, utility_exterior_height xml_real64, utility_exterior_height_units xml_buffer, utility_exterior_diameter xml_real64, utility_exterior_diameter_units xml_buffer, utility_interior_diameter xml_real64, utility_interior_diameter_units xml_buffer
roundpipe: Inspector [off]

Bookmark: Network ID
UUIDGenerator_4
    UUID_ATTR = Network_ID
    -> StringConcatenator_4
StringConcatenator_4
    PARM_LINE = NetworkID_@Value(Network_ID)
    ATTRLIST = Network_ID
    ACTION = Overwrite Existing Attributes
    -> UUIDGenerator_5

Bookmark: NetworkGraph ID
UUIDGenerator_5
    UUID_ATTR = NetworkGraph_ID
    -> StringConcatenator_5
StringConcatenator_5
    PARM_LINE = NetworkGraphID_@Value(NetworkGraph_ID)
    ATTRLIST = NetworkGraph_ID
    ACTION = Overwrite Existing Attributes
    -> UUIDGenerator_7
    -> FeatureMerger_2 [SUPPLIER]
    -> FeatureMerger_9 [SUPPLIER]
    -> AttributeCreator_24
    -> FeatureMerger_11 [SUPPLIER]

Bookmark: LiquidMedium ID
UUIDGenerator_7
    UUID_ATTR = LiquidMedium_ID
    -> StringConcatenator_7
StringConcatenator_7
    PARM_LINE = LiquidMediumID_@Value(LiquidMedium_ID)
    ATTRLIST = LiquidMedium_ID
    ACTION = Overwrite Existing Attributes
    -> AttributeCreator_5
    -> AttributeCreator_9

Bookmark: Appurtenaces
AttributeFilter_4
    ATTR_NAME = TYPE
    ATTR_VALUES = <Empty>,<Missing>,<Null>,<Unfiltered>,Air Release Vale,Butterfly Valve,Cathotic Testing Sta,Check Valve,Clean Port,Endcap,Gate Valve,Junction,Meter,Pressure Reducing Va,Private Hydrant,Public Hydrant,Pump,Reducer,Reservoir,Scour Valve,Surge Tank
    Junction -> UUIDGenerator_6
AttributeRenamer_29
    ATTR_TABLE = RENAME_SET_DEFAULT Node_ID > Junction_Node_ID
    -> AttributeRemover_2
    -> AttributeRemover_4
AttributeCreator_45
    ATTR_TABLE = SET_TO citygml_feature_role = nodeMember
    -> AttributeRenamer_32
AttributeRenamer_32
    ATTR_TABLE:
      RENAME_SET_DEFAULT Node_ID > gml_id
      RENAME_SET_DEFAULT FeatureGraph_ID > gml_parent_id
    -> Node (writer CITYGML_1)
AttributeCreator_47
    ATTR_TABLE = SET_TO citygml_feature_role = featureGraphMember
    -> AttributeRenamer_35
AttributeRenamer_35
    ATTR_TABLE:
      RENAME_SET_DEFAULT FeatureGraph_ID > gml_id
      RENAME_SET_DEFAULT NetworkGraph_ID > gml_parent_id
    -> FeatureGraph (writer CITYGML_1)
AttributeCreator_40
    ATTR_TABLE = SET_TO citygml_feature_role = component
    -> AttributeRenamer_26
AttributeRenamer_26
    ATTR_TABLE:
      RENAME_SET_DEFAULT Junction_ID > gml_id
      RENAME_SET_DEFAULT Network_ID > gml_parent_id
    -> AttributeRenamer_27
AttributeRenamer_27
    ATTR_TABLE = RENAME_SET_DEFAULT FeatureGraph_ID > utility_topo_graph_xlink_href
    -> StringConcatenator_32
StringConcatenator_32
    PARM_LINE = #@Value(utility_topo_graph_xlink_href)
    ATTRLIST = utility_topo_graph_xlink_href
    ACTION = Overwrite Existing Attributes
    -> SimpleFunctionalElement (writer CITYGML_1)
SimpleFunctionalElement (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64,
      utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer,
      utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer

Bookmark: Junction ID
UUIDGenerator_6
    UUID_ATTR = Junction_ID
    -> StringConcatenator_6
StringConcatenator_6
    PARM_LINE = JunctionID_@Value(Junction_ID)
    ATTRLIST = Junction_ID
    ACTION = Overwrite Existing Attributes
    -> UUIDGenerator_19

Bookmark: FeatureGraph ID
UUIDGenerator_19
    UUID_ATTR = FeatureGraph_ID
    -> StringConcatenator_28
StringConcatenator_28
    PARM_LINE = FeatureGraphID_@Value(FeatureGraph_ID)
    ATTRLIST = FeatureGraph_ID
    ACTION = Overwrite Existing Attributes
    -> UUIDGenerator_20

Bookmark: Node ID
UUIDGenerator_20
    UUID_ATTR = Node_ID
    -> StringConcatenator_29
StringConcatenator_29
    PARM_LINE = Node_ID_@Value(Node_ID)
    ATTRLIST = Node_ID
    ACTION = Overwrite Existing Attributes
    -> AttributeCreator_37
    -> AttributeCreator_41
    -> AttributeCreator_47

Bookmark: Set CityGML Geometry
AttributeCreator_41
    ATTR_TABLE = SET_TO citygml_lod_name = realization
    -> GeometryPropertySetter_10
GeometryPropertySetter_10
    REMOVE_ATTRIBUTE = No
    SRC_ATTRS = citygml_lod_name
    OVERWRITE_CHOICE = Yes
    SETTYPE_PARAM = Traits From Attributes
    SET -> AttributeCreator_45
    SET -> AttributeRenamer_29

Bookmark: Set CityGML Geometry
AttributeCreator_37
    ATTR_TABLE = SET_TO citygml_lod_name = lod1Geometry
    -> GeometryPropertySetter_9
GeometryPropertySetter_9
    REMOVE_ATTRIBUTE = No
    SRC_ATTRS = citygml_lod_name
    OVERWRITE_CHOICE = Yes
    SETTYPE_PARAM = Traits From Attributes
    SET -> AttributeCreator_38

Bookmark: Junction attributes
AttributeCreator_38
    ATTR_TABLE:
      SET_TO utility_status = inUse
      SET_TO utility_function = junction
    -> AttributeValueMapper_6
AttributeValueMapper_6
    SRC = TYPE
    LUT = ASBUILT,assumed,BCASS,unknown,DRAWING,calculated,FIELD NOTE,assumed,GPS,surveyed,LEGAL PLAN,calculated,ORTHOPHOTO,estimated,PHGRAMM,surveyed,SURVEYED,surveyed,,unknown
    DEFAULT_VALUE = unknown
    VAL_ATTR = utility_location_quality
    DIRECTION = Forward (Source To Destination)
    -> AttributeCreator_39
AttributeCreator_39
    ATTR_TABLE = SET_TO utility_elevation_quality = estimated
    -> AttributeCreator_42
AttributeCreator_42
    ATTR_TABLE = SET_TO utility_class = unknown
    -> AttributeCreator_40

Bookmark: Remove orphan service lines
  Some service line features are not connected to a pipe feature, nor another service line feature..  This is simply due to incomplete source data  These are referred to as "oprhan service lines", and are removed.
SpatialRelator_2
    AGGREGATE_HANDLING = Yes
    CALC_CARD = No
    CURVE_BOUNDARY_RULE_PARAM = Default Rule
    PREDICATES = TOUCHES
    SUCCESS_ATTR = _related_candidates
    -> AttributeRangeFilter
SpatialRelator
    AGGREGATE_HANDLING = Yes
    CALC_CARD = No
    CURVE_BOUNDARY_RULE_PARAM = Default Rule
    PREDICATES = TOUCHES
    SUCCESS_ATTR = _related_candidates
    -> AttributeRangeFilter
AttributeRangeFilter
    IN_ATTR = _related_candidates
    LUT = 0,0,ORPHAN
    <UNFILTERED> -> DuplicateFilter
DuplicateFilter
    KEYATTR = GID
    INPUT_ORDERED_CHOICE = No
    UNIQUE -> UUIDGenerator_2
AttributeCreator_20
    ATTR_TABLE = SET_TO TYPE = houseServiceLine
    -> FeatureHolder_2

Bookmark: Service Line ID
UUIDGenerator_2
    UUID_ATTR = ServiceLine_ID
    -> StringConcatenator_2
StringConcatenator_2
    PARM_LINE = ServiceLineID_@Value(ServiceLine_ID)
    ATTRLIST = ServiceLine_ID
    ACTION = Overwrite Existing Attributes
    -> TopologyBuilder
    -> AttributeCreator_20

Bookmark: Find end of service line that is on the parcel and the end on the pipe
  The service line should have one end on the parcel (ultimately leading to the TerminalElement), and another on the pipes.  We differentiate between them by created an attribute called "service_end", which can be either "JUNCTION" Or "TO_TERMINAL"
TopologyBuilder
    ALLOW_CYCLES = No
    MAX = 0
    PROP_ATTRS = Yes
    BOUNDING_EDGES = All
    CLEAN_DATA = Yes
    OVERLAPPING_MODE = No
    DEAGGREGATE_INPUT = Yes
    NODE -> PointOnLineOverlayer [POINT]
AttributeRenamer
    ATTR_TABLE = RENAME_SET_DEFAULT RoundPipe_ID > Parent_RoundPipe_ID
    -> PointOnLineOverlayer [LINE]
PointOnLineOverlayer
    ATTR_CONFLICT_RES = Use Original
    DEAGGREGATE_INPUT = Yes
    ATTR_ACCUM_MODE = Merge Incoming
    OV_ATTR = on_pipe
    TOLERANCE = 0.01
    POINT -> AttributeRangeFilter_2
AttributeRangeFilter_2
    IN_ATTR = on_pipe
    LUT = 1,1,no,2,9999,yes
    no -> PointOnAreaOverlayer [POINT]
    yes -> PointOnLineOverlayer_2 [POINT]
AttributeRenamer_2
    ATTR_TABLE = RENAME_SET_DEFAULT Parcel_ID > Parent_ParcelID
    -> PointOnAreaOverlayer [AREA]
PointOnAreaOverlayer
    ATTR_CONFLICT_RES = Use Original
    CANDIDATE_LIST_ATTRS_TO_INCLUDE_MODE = Selected Attributes
    DEAGGREGATE_INPUT = Yes
    ATTR_ACCUM_MODE = Merge Incoming
    OV_ATTR = _overlaps
    POLYS_FIRST = No
    POINT -> CoordinateExtractor_2

Bookmark: RoundPipe ID
UUIDGenerator_12
    UUID_ATTR = RoundPipe_ID
    -> StringConcatenator_11
StringConcatenator_11
    PARM_LINE = RoundPipeID_@Value(RoundPipe_ID)
    ATTRLIST = RoundPipe_ID
    ACTION = Overwrite Existing Attributes
    -> UUIDGenerator_13

Bookmark: FeatureGraph ID
UUIDGenerator_13
    UUID_ATTR = FeatureGraph_ID
    -> StringConcatenator_15
StringConcatenator_15
    PARM_LINE = FeatureGraphID_@Value(FeatureGraph_ID)
    ATTRLIST = FeatureGraph_ID
    ACTION = Overwrite Existing Attributes
    -> FeatureMerger_9 [REQUESTOR]

Bookmark: InteriorFeatureLink ID
UUIDGenerator_18
    UUID_ATTR = InteriorFeatureLink_ID
    -> StringConcatenator_18
StringConcatenator_18
    PARM_LINE = InteriorFeatureLinkID_@Value(InteriorFeatureLink_ID)
    ATTRLIST = InteriorFeatureLink_ID
    ACTION = Overwrite Existing Attributes
    -> FeatureMerger_3 [REQUESTOR]

Bookmark: Node ID
UUIDGenerator_11
    UUID_ATTR = Node_ID
    -> StringConcatenator_10
StringConcatenator_10
    PARM_LINE = NodeID_@Value(Node_ID)
    ATTRLIST = Node_ID
    ACTION = Overwrite Existing Attributes
    -> FeatureMerger_3 [SUPPLIER]
    -> FeatureMerger_4 [SUPPLIER]
    -> FeatureMerger_14 [REQUESTOR]
    -> FeatureMerger_14 [SUPPLIER]
    -> AttributeRenamer_17
    -> FeatureMerger_5 [REQUESTOR]
    -> inspector1_2

Bookmark: Connect InteriorFeatureLinks with Nodes
Note: Connect InteriorFeatureLinks with Nodes. / Now InteriorFeatureLinks have attributes of Nodes / So InteriorFeatureLinks can have a reference to a start Node
FeatureMerger_3
    ATTR_CONFLICT_RES = Use Requestor
    IGNORE_NULLS = No
    PROCESS_DUPS = No
    MERGE_TYPE = Attributes Only
    REJECT_NULL_MISSING_KEYS = No
    JOIN_KEYS = @Value(_edge_id) @Value(fme_arc_id) AUTO @Value(_from_node) @Value(_node_number) AUTO
    SUPPLIERS_FIRST = No
    ATTR_ACCUM_MODE = Merge Supplier
    MERGED -> AttributeRenamer_7
Note: Set XLink reference between / InteriorFeatureLink and start / nodes
AttributeRenamer_7
    ATTR_TABLE = RENAME_SET_DEFAULT Node_ID > utility_start_xlink_href
    -> FeatureMerger_4 [REQUESTOR]
Note: Connect InteriorFeatureLinks with Nodes. / Now InteriorFeatureLinks have attributes of Nodes / So InteriorFeatureLinks can have a reference to a end Node
FeatureMerger_4
    ATTR_CONFLICT_RES = Use Requestor
    IGNORE_NULLS = No
    PROCESS_DUPS = No
    MERGE_TYPE = Attributes Only
    REJECT_NULL_MISSING_KEYS = No
    JOIN_KEYS = @Value(_edge_id) @Value(fme_arc_id) AUTO @Value(_to_node) @Value(_node_number) AUTO
    SUPPLIERS_FIRST = No
    ATTR_ACCUM_MODE = Merge Supplier
    MERGED -> AttributeRenamer_8
Note: Set XLink reference between / InteriorFeatureLink and end / nodes
AttributeRenamer_8
    ATTR_TABLE = RENAME_SET_DEFAULT Node_ID > utility_end_xlink_href
    -> 3DForcer_2
    -> FeatureMerger_5 [SUPPLIER]
    -> FeatureMerger_6 [SUPPLIER]

Bookmark: Set CityGML Geometry
3DForcer_2
    ZVALATTR = 0
    KEEPZVAL = No
    -> AttributeCreator_3
AttributeCreator_3
    ATTR_TABLE = SET_TO citygml_lod_name = realization
    -> GeometryPropertySetter_2
GeometryPropertySetter_2
    REMOVE_ATTRIBUTE = No
    SRC_ATTRS = citygml_lod_name
    OVERWRITE_CHOICE = Yes
    SETTYPE_PARAM = Traits From Attributes
    SET -> AttributeCreator_6

Bookmark: InterFeatureLink ID
UUIDGenerator_22
    UUID_ATTR = InterFeatureLink_ID
    -> StringConcatenator_36
StringConcatenator_36
    PARM_LINE = InterFeatureLinkID_@Value(InterFeatureLink_ID)
    ATTRLIST = InterFeatureLink_ID
    ACTION = Overwrite Existing Attributes
    -> 3DForcer_3

Bookmark: Set CityGML Geometry
3DForcer_3
    ZVALATTR = 0
    KEEPZVAL = No
    -> AttributeCreator_7
AttributeCreator_7
    ATTR_TABLE = SET_TO citygml_lod_name = realization
    -> GeometryPropertySetter_3
GeometryPropertySetter_3
    REMOVE_ATTRIBUTE = No
    SRC_ATTRS = citygml_lod_name
    OVERWRITE_CHOICE = Yes
    SETTYPE_PARAM = Traits From Attributes
    SET -> AttributeCreator_8

Bookmark: InterFeatureLink ID
UUIDGenerator_21
    UUID_ATTR = InterFeatureLink_ID
    -> StringConcatenator_33
StringConcatenator_33
    PARM_LINE = InterFeatureLinkID_@Value(InterFeatureLink_ID)
    ATTRLIST = InterFeatureLink_ID
    ACTION = Overwrite Existing Attributes
    -> AttributeCreator_46

Bookmark: InterFeatureLinks
Note: Connect nodes with themselves
FeatureMerger_14
    ATTR_CONFLICT_RES = Use Requestor
    IGNORE_NULLS = No
    PROCESS_DUPS = Yes
    GEOM_TYPE = Build Polygons
    MERGE_TYPE = Attributes Only
    REJECT_NULL_MISSING_KEYS = No
    JOIN_KEYS = @Value(_node_number) @Value(_node_number) AUTO
    CONNECT_Z_MODE = First Wins
    SUPPLIERS_FIRST = No
    ATTR_ACCUM_MODE = Merge Supplier
    LIST_NAME = _list
    LIST_ATTRS_TO_INCLUDE = _element_index _node_number ACCURACY ASBUILT CATCHMENT DIAMETER ENDID fme_arc_angle fme_arc_id GID LENGTH MATERIAL Node_ID OWNER PIPEID STARTID TYPE WATERCATEG YEAR
    MERGED -> AttributeRenamer_22
Note: Rename Node_ID to / Node_ID_original
AttributeRenamer_22
    ATTR_TABLE = RENAME_SET_DEFAULT Node_ID > Node_ID_original
    -> ListExploder_6
Note: See slides for InterFeatureLinks
ListExploder_6
    LIST_ATTR = _list{}
    ATTR_ACCUM_MODE = Merge Incoming List
    INDEX_ATTR = _element_index
    ATTR_CONFLICT_RES = Use Original
    LIST_FOUND -> AttributeRenamer_23
Note: Rename Node_ID to / Node_ID_merged
AttributeRenamer_23
    ATTR_TABLE = RENAME_SET_DEFAULT Node_ID > Node_ID_merged
    -> TestFilter
Note: Keep only nodes for which / Node_ID_original = Node_ID_merged
TestFilter
    TEST_LIST = BOOL_OP,OR,COMPOSITE_TEST,<Unused>,TEST_CLAUSE,"TEST @Value(Node_ID_original) != @Value(Node_ID_merged)",@Value(Node_ID_original) < @Value(Node_ID_merged)
    DEFAULT_VALUE = <UNFILTERED>
    @Value(Node_ID_original) < @Value(Node_ID_merged) -> TestFilter_2
Note: See slides for / InterFeatureLinks
TestFilter_2
    TEST_LIST = BOOL_OP,OR,COMPOSITE_TEST,<Unused>,TEST_CLAUSE,"TEST @Value(Node_ID_original) < @Value(Node_ID_merged)",@Value(Node_ID_original) < @Value(Node_ID_merged)
    DEFAULT_VALUE = <UNFILTERED>
    @Value(Node_ID_original) < @Value(Node_ID_merged) -> UUIDGenerator_14
Note: Rename Node_ID_original to utility_start_xlink_href / and Node_ID_merged to utility_end_xink_href
AttributeRenamer_24
    ATTR_LIST = Node_ID_original,utility_start_xlink_href,,Node_ID_merged,utility_end_xlink_href,
    -> StringConcatenator_25
StringConcatenator_25
    PARM_LINE = #@Value(utility_start_xlink_href)
    ATTRLIST = utility_start_xlink_href
    ACTION = Overwrite Existing Attributes
    -> StringConcatenator_26
StringConcatenator_26
    PARM_LINE = #@Value(utility_end_xlink_href)
    ATTRLIST = utility_end_xlink_href
    ACTION = Overwrite Existing Attributes
    -> GeometryRemover_3
Note: See slides for InterFeatureLinks
GeometryRemover_3
    -> AttributeCreator_19
Note: Set utility_type = connects
AttributeCreator_19
    ATTR_TABLE = SET_TO utility_type = connects
    -> AttributeCreator_27
Note: Set relationship between InterFeatureLink / and NetworkGraph (+linkMember)
AttributeCreator_27
    ATTR_LIST = citygml_feature_role,linkMember
    -> AttributeRenamer_25
Note: Set gml_id to InterFeatureLink_ID / and gml_parent_id to NetworkGraph_ID
AttributeRenamer_25
    ATTR_LIST = InterFeatureLink_ID,gml_id,,NetworkGraph_ID,gml_parent_id,
    -> InterFeatureLink (writer CITYGML_1)

Bookmark: InterFeatureLink ID
UUIDGenerator_14
    UUID_ATTR = InterFeatureLink_ID
    -> StringConcatenator_14
StringConcatenator_14
    PARM_LINE = InterFeatureLinkID_@Value(InterFeatureLink_ID)
    ATTRLIST = InterFeatureLink_ID
    ACTION = Overwrite Existing Attributes
    -> AttributeRenamer_24

Bookmark: ExteriorMaterial ID
UUIDGenerator_10
    UUID_ATTR = ExteriorMaterial_ID
    -> StringConcatenator_9
StringConcatenator_9
    PARM_LINE = ExteriorMaterialID_@Value(ExteriorMaterial_ID)
    ATTRLIST = ExteriorMaterial_ID
    ACTION = Overwrite Existing Attributes
    -> FeatureMerger_7 [SUPPLIER]
    -> AttributeRenamer_12

Bookmark: Set CityGML Geometry
AttributeCreator_35
    ATTR_TABLE = SET_TO citygml_lod_name = realization
    -> GeometryPropertySetter_6
GeometryPropertySetter_6
    REMOVE_ATTRIBUTE = No
    SRC_ATTRS = citygml_lod_name
    OVERWRITE_CHOICE = Yes
    SETTYPE_PARAM = Traits From Attributes
    SET -> FeatureGraph (writer CITYGML_1)

Bookmark: Clean up parcels
  The parcels are not suitable for analysis in their source format.  Some parcels contain a duplex house, and that is reflected in the parcel by a small partioned inner polygon.  Other parcels appear to be individual features called "Strata Lots" that are fully contained by "Strata" features.  Here, we dissolve the duplex lot features and use the individual Strata Lot features to erase the Strata features.
AttributeFilter
    ATTR_NAME = TYPE
    ATTR_VALUES = <Empty>,<Missing>,<Null>,<Unfiltered>,Strata,BARE LAND STRATA,Building,Air Space
    <UNFILTERED> -> AttributeFilter_2
    Strata -> Dissolver
    BARE LAND STRATA -> Dissolver
    Building -> Dissolver
Dissolver
    ACCUM_INPUT_ATTRS = Use Attributes From One Feature
    GROUP_BY = PLAN
    DEAGGREGATE_INPUT = Yes
    CONNECT_Z_MODE = First Wins
    NO_OVRLP = No
    AREA -> AttributeFilter_2
AttributeFilter_2
    ATTR_NAME = TYPE
    ATTR_VALUES = <Empty>,<Missing>,<Null>,<Unfiltered>,Strata Lot
    <UNFILTERED> -> Clipper [CLIPPEE]
    Strata Lot -> Clipper [CLIPPER]
Clipper
    ATTR_CONFLICT_RES = Use Clippee
    LINES_AS_SEGMENTS = No
    CREATE_AGGREGATES = Yes
    BOUNDARY_CASES = Treat as Inside
    VAL_SOURCE = Clippee Only
    DEFAULT_VAL = 0
    MISSING_VAL_MODE = Compute
    PRESERVE_CLIPPEE_EXTENTS = No
    CONNECT_Z_MODE = First Wins
    MEASURE_TYPE = Continuous
    ATTR_ACCUM_MODE = Merge Clipper
    CLIP_TYPE = Multiple Clippers
    CLIPPED_ATTR = _clipped
    INSIDE -> UUIDGenerator_9
    OUTSIDE -> UUIDGenerator_9
UUIDGenerator_9
    UUID_ATTR = Parcel_ID
    -> AttributeRenamer_2
    -> SpatialRelator_3 [Supplier]
    -> parcels
    -> PointOnAreaOverlayer_2 [AREA]

Bookmark: Buildings
SpatialFilter_4
    AGGREGATE_HANDLING = Yes
    ATTR_CONFLICT_RES = Use Candidate
    BASE_TYPE = Multiple Filters
    PREDATTR = _predicate
    USE_BOUNDING_BOX = No
    CURVE_BOUNDARY_RULE_PARAM = Default Rule
    PASS_CRITERIA = Pass Against One Filter
    ATTR_ACCUM_MODE = Merge Filter
    PREDICATES = INTERSECTS
    PASSED -> FeatureMerger_2 [REQUESTOR]
FeatureMerger_2
    ATTR_CONFLICT_RES = Use Requestor
    IGNORE_NULLS = No
    PROCESS_DUPS = No
    MERGE_TYPE = Attributes Only
    REJECT_NULL_MISSING_KEYS = No
    JOIN_KEYS = 1 1 AUTO
    SUPPLIERS_FIRST = No
    ATTR_ACCUM_MODE = Merge Supplier
    MERGED -> SpatialRelator_3 [Requestor]
SpatialRelator_3
    AGGREGATE_HANDLING = Yes
    ATTR_CONFLICT_RES = Use Requestor
    CALC_CARD = No
    CURVE_BOUNDARY_RULE_PARAM = Default Rule
    ATTR_ACCUM_MODE = Merge Supplier
    PREDICATES = INTERSECTS
    SUCCESS_ATTR = _related_candidates
    -> UUIDGenerator_15
GEOTIFF (reader GEOTIFF_2)
    -> SurfaceDraper_4 [POINTS/LINES]
SurfaceDraper_4
    DRAPE_TYPE = VERTEX
    ADDZ_TYPE = Offset Z
    INTERPOLATION_TYPE = AUTO
    TOLERANCE = -2
    DRAPED_FEATURES -> CenterPointReplacer_2
CenterPointReplacer_2
    MODE = Center of Gravity Point
    POINT -> PointOnAreaOverlayer_2 [POINT]
    POINT -> CoordinateExtractor
    POINT -> AttributeRenamer_15
    POINT -> AttributeCreator_17
Note: Set type = exterior
AttributeCreator_17
    ATTR_TABLE = SET_TO utility_type = exterior
    -> 3DForcer_4
Note: Set relation between FeatureGraph / and Node (+nodeMember)
AttributeCreator_16
    ATTR_TABLE = SET_TO citygml_feature_role = nodeMember
    -> AttributeRenamer_18
Note: Set gml_id to Node_ID / and gml_parent_id to FeatureGraph_ID
AttributeRenamer_18
    ATTR_TABLE:
      RENAME_SET_DEFAULT Node_ID > gml_id
      RENAME_SET_DEFAULT FeatureGraph_ID > gml_parent_id
    -> Node (writer CITYGML_1)
    -> terminalelements_nodes
terminalelements_nodes: Inspector [off]
Note: Remove Geometry because it is / irrelevant for FeatureGraphs
GeometryRemover_2
    -> AttributeCreator_18
Note: Set relationship between FeatureGraph / and NetworkGraph (+featureGraphMember)
AttributeCreator_18
    ATTR_TABLE = SET_TO citygml_feature_role = featureGraphMember
    -> AttributeRenamer_21
Note: Set gml_id (FeatureGraph_ID) / and gml_parent_id (NetworkGraph_ID)
AttributeRenamer_21
    ATTR_TABLE:
      RENAME_SET_DEFAULT FeatureGraph_ID > gml_id
      RENAME_SET_DEFAULT NetworkGraph_ID > gml_parent_id
    -> FeatureGraph (writer CITYGML_1)
PointOnAreaOverlayer_2
    ATTR_CONFLICT_RES = Use Original
    CANDIDATE_LIST_ATTRS_TO_INCLUDE_MODE = Selected Attributes
    DEAGGREGATE_INPUT = Yes
    ATTR_ACCUM_MODE = Merge Incoming
    OV_ATTR = _overlaps
    POLYS_FIRST = No
    POINT -> 2DForcer
AttributeRenamer_15
    ATTR_TABLE:
      RENAME_SET_DEFAULT TerminalElement_ID > gml_id
      RENAME_SET_DEFAULT Network_ID > gml_parent_id
      RENAME_SET_DEFAULT Building_ID > utility_connected_city_object
      RENAME_SET_DEFAULT FeatureGraph_ID > utility_topo_graph_xlink_href
    -> StringConcatenator_22
StringConcatenator_22
    PARM_LINE = #@Value(utility_topo_graph_xlink_href)
    ATTRLIST = utility_topo_graph_xlink_href
    ACTION = Overwrite Existing Attributes
    -> AttributeCreator_13
AttributeCreator_13
    ATTR_TABLE = SET_TO citygml_feature_role = component
    -> AttributeCreator_12
TerminalElement (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_medium_supply{}.utility_electrical_medium_supply_utility_potential_supply_utility_supply_utility_flow_rate xml_real64,
      utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29), utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer,
      utility_medium_supply{}.utility_gaseous_medium_supply_utility_type xml_buffer, utility_medium_supply{}.utility_gaseous_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64,
      utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer
terminalelements: Inspector [off]
CoordinateExtractor
    Z_ATTR = _z
    Y_ATTR = _y
    MODE = Specify Coordinate
    IND = 0
    X_ATTR = _x
    -> FeatureMerger_10 [SUPPLIER]
FeatureMerger_10
    ATTR_CONFLICT_RES = Use Requestor
    IGNORE_NULLS = No
    PROCESS_DUPS = No
    MERGE_TYPE = Attributes Only
    REJECT_NULL_MISSING_KEYS = No
    JOIN_KEYS = @Value(Building_ID) @Value(Building_ID) AUTO
    SUPPLIERS_FIRST = No
    ATTR_ACCUM_MODE = Merge Supplier
    MERGED -> Offsetter_3
Offsetter_3
    ZOFF = @Value(_z)
    YOFF = 0
    MODE = Cartesian Coordinate
    XOFF = 0
    OFFSET -> Extruder
Extruder
    DISTANCE = 3+(@Value(FLOORS)*3)-1
    DIRECTION = Vertical
    EXTRUDED -> AttributeRenamer_19
AttributeRenamer_19
    ATTR_TABLE = RENAME_SET_DEFAULT Building_ID > gml_id
    -> StringConcatenator_12
StringConcatenator_12
    PARM_LINE = @Value(HOUSENUMBE) @Value(STREETNAME) @Value(POSTALCODE)
    ACTION = Create New Attribute
    VAL_ATTR = gml_name
    -> AttributeCreator_23
Building (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_medium_supply{}.utility_electrical_medium_supply_utility_potential_supply_utility_supply_utility_flow_rate xml_real64,
      utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29), utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer,
      utility_medium_supply{}.utility_liquid_medium_supply_utility_type xml_buffer, utility_medium_supply{}.utility_liquid_medium_supply_utility_type_codeSpace xml_buffer, utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64,
      utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_role_in_network{}.xlink_href xml_buffer, citygml_appearance{}.xlink_href xml_buffer, citygml_class xml_buffer, citygml_class_codeSpace xml_buffer, citygml_function{} xml_buffer, citygml_function{}.codeSpace xml_buffer, citygml_usage{} xml_buffer, citygml_usage{}.codeSpace xml_buffer,
      citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, utility_building_habitants{} xml_int64
buildings: Inspector [off]

Bookmark: Building ID
UUIDGenerator_15
    UUID_ATTR = Building_ID
    -> StringConcatenator_13
StringConcatenator_13
    PARM_LINE = BuildingID_@Value(Building_ID)
    ATTRLIST = Building_ID
    ACTION = Overwrite Existing Attributes
    -> UUIDGenerator_17

Bookmark: TerminalElement ID
UUIDGenerator_17
    UUID_ATTR = TerminalElement_ID
    -> StringConcatenator_16
StringConcatenator_16
    PARM_LINE = TerminalElementID_@Value(TerminalElement_ID)
    ATTRLIST = TerminalElement_ID
    ACTION = Overwrite Existing Attributes
    -> UUIDGenerator_16

Bookmark: FeatureGraph ID
UUIDGenerator_16
    UUID_ATTR = FeatureGraph_ID
    -> StringConcatenator_17
StringConcatenator_17
    PARM_LINE = FeatureGraphID_@Value(FeatureGraph_ID)
    ATTRLIST = FeatureGraph_ID
    ACTION = Overwrite Existing Attributes
    -> UUIDGenerator_3

Bookmark: Node ID
UUIDGenerator_3
    UUID_ATTR = Node_ID
    -> StringConcatenator_3
StringConcatenator_3
    PARM_LINE = Node_ID_@Value(Node_ID)
    ATTRLIST = Node_ID
    ACTION = Overwrite Existing Attributes
    -> SurfaceDraper_4 [DRAPE_FEATURES]
    -> FeatureMerger_10 [REQUESTOR]

Bookmark: Set CityGML Geometry
3DForcer_4
    ZVALATTR = 0
    KEEPZVAL = No
    -> AttributeCreator_15
AttributeCreator_15
    ATTR_TABLE = SET_TO citygml_lod_name = realization
    -> GeometryPropertySetter_5
GeometryPropertySetter_5
    REMOVE_ATTRIBUTE = No
    SRC_ATTRS = citygml_lod_name
    OVERWRITE_CHOICE = Yes
    SETTYPE_PARAM = Traits From Attributes
    SET -> AttributeCreator_16
    SET -> GeometryRemover_2

Bookmark: InterFeatureLink ID
UUIDGenerator_8
    UUID_ATTR = InterFeatureLink_ID
    -> StringConcatenator_8
StringConcatenator_8
    PARM_LINE = InterFeatureLinkID_@Value(InterFeatureLink_ID)
    ATTRLIST = InterFeatureLink_ID
    ACTION = Overwrite Existing Attributes
    -> AttributeCreator_14

Bookmark: Set CityGML Geometry
AttributeCreator_36
    ATTR_TABLE = SET_TO citygml_lod_name = realization
    -> GeometryPropertySetter_8
GeometryPropertySetter_8
    REMOVE_ATTRIBUTE = No
    SRC_ATTRS = citygml_lod_name
    OVERWRITE_CHOICE = Yes
    SETTYPE_PARAM = Traits From Attributes
    SET -> InterFeatureLink (writer CITYGML_1)

Bookmark: Set CityGML Geometry
AttributeCreator_12
    ATTR_TABLE = SET_TO citygml_lod_name = lod1Geometry
    -> GeometryPropertySetter_4
GeometryPropertySetter_4
    REMOVE_ATTRIBUTE = No
    SRC_ATTRS = citygml_lod_name
    OVERWRITE_CHOICE = Yes
    SETTYPE_PARAM = Traits From Attributes
    SET -> AttributeCreator_32

Bookmark: TerminalElement attributes
AttributeCreator_32
    ATTR_TABLE = SET_TO function = draining
    -> AttributeCreator_33
AttributeCreator_33
    ATTR_TABLE = SET_TO usage = draining
    -> AttributeCreator_10
AttributeCreator_10
    ATTR_TABLE = SET_TO utility_status = inUse
    -> AttributeValueMapper_8
AttributeValueMapper_8
    SRC = TYPE
    LUT = ASBUILT,assumed,BCASS,unknown,DRAWING,calculated,FIELD NOTE,assumed,GPS,surveyed,LEGAL PLAN,calculated,ORTHOPHOTO,estimated,PHGRAMM,surveyed,SURVEYED,surveyed,,unknown
    DEFAULT_VALUE = unknown
    VAL_ATTR = utility_location_quality
    DIRECTION = Forward (Source To Destination)
    -> AttributeCreator_31
AttributeCreator_31
    ATTR_TABLE = SET_TO utility_elevation_quality = estimated
    -> AttributeCreator_34
AttributeCreator_34
    ATTR_TABLE = SET_TO utility_class = unknown
    -> TerminalElement (writer CITYGML_1)
    -> terminalelements

Bookmark: Set CityGML Geometry
AttributeCreator_23
    ATTR_TABLE = SET_TO citygml_lod_name = lod1Solid
    -> GeometryPropertySetter_7
GeometryPropertySetter_7
    REMOVE_ATTRIBUTE = No
    SRC_ATTRS = citygml_lod_name
    OVERWRITE_CHOICE = Yes
    SETTYPE_PARAM = Traits From Attributes
    SET -> Building (writer CITYGML_1)
    SET -> buildings

Bookmark: Make features 3D and set CityGML geometry
GEOTIFF (reader GEOTIFF_1)
    -> SurfaceDraper [POINTS/LINES]
SurfaceDraper
    DRAPE_TYPE = VERTEX
    ADDZ_TYPE = Replace Z
    INTERPOLATION_TYPE = AUTO
    TOLERANCE = -2
    DRAPED_FEATURES -> Offsetter
Offsetter
    ZOFF = -2
    YOFF = 0
    MODE = Cartesian Coordinate
    XOFF = 0
    OFFSET -> AttributeCreator_2
AttributeCreator_2
    ATTR_TABLE:
      SET_TO citygml_lod_name = lod1Geometry
      SET_TO utility_has_material{0}.xlink_href = hasMaterial
    -> GeometryPropertySetter
GeometryPropertySetter
    REMOVE_ATTRIBUTE = No
    SRC_ATTRS = citygml_lod_name
    OVERWRITE_CHOICE = Yes
    SETTYPE_PARAM = Traits From Attributes
    SET -> AttributeCreator

Bookmark: Set RoundPipe attributes
FeatureMerger_15
    ATTR_CONFLICT_RES = Use Requestor
    IGNORE_NULLS = No
    PROCESS_DUPS = No
    MERGE_TYPE = Attributes Only
    REJECT_NULL_MISSING_KEYS = No
    JOIN_KEYS = @Value(RoundPipe_ID) @Value(RoundPipe_ID) AUTO
    SUPPLIERS_FIRST = No
    ATTR_ACCUM_MODE = Merge Supplier
    MERGED -> AttributeRenamer_13
AttributeRenamer_13
    ATTR_TABLE = RENAME_SET_DEFAULT FeatureGraph_ID > utility_topo_graph_xlink_href
    -> StringConcatenator_21
StringConcatenator_21
    PARM_LINE = #@Value(utility_topo_graph_xlink_href)
    ATTRLIST = utility_topo_graph_xlink_href
    ACTION = Overwrite Existing Attributes
    -> AttributeValueMapper_2
AttributeValueMapper_2
    SRC = TYPE
    LUT = Primary Distribution,distribution,Primary Supply,feeding,Secondary Distributi,distribution,Secondary Supply,feeding,houseServiceLine,houseServiceLine
    DEFAULT_VALUE = unknown
    VAL_ATTR = utility_function
    DIRECTION = Forward (Source To Destination)
    -> AttributeValueMapper_3
Note: needs to be list
AttributeValueMapper_3
    SRC = TYPE
    LUT = Primary Distribution,distribution,Primary Supply,feeding,Secondary Distributi,distribution,Secondary Supply,feeding,houseServiceLine,houseServiceLine
    DEFAULT_VALUE = unknown
    VAL_ATTR = utility_usage
    DIRECTION = Forward (Source To Destination)
    -> AttributeRangeFilter_3
AttributeRangeFilter_3
    IN_ATTR = YEAR
    LUT = 1800,2200,good,0,0,invalid
    good -> AttributeCreator_29
    invalid -> AttributeCreator_30
    <UNFILTERED> -> AttributeCreator_30
AttributeCreator_29
    ATTR_TABLE = SET_TO utility_year_of_construction = @Value(YEAR)-01-01
    -> AttributeCreator_21
AttributeCreator_30
    ATTR_TABLE = SET_TO utility_year_of_construction = 0001-01-01
    -> AttributeCreator_21
AttributeCreator_21
    ATTR_TABLE = SET_TO utility_status = inUse
    -> AttributeValueMapper_4
Note: TEMPEST
AttributeValueMapper_4
    SRC = TYPE
    LUT = ASBUILT,assumed,FIELD,surveyed,GPS,surveyed,ORTHOPHOTO,estimated,TEMPEST,TEMPEST,Unknown,unknown,UNKNOWN,unknown
    DEFAULT_VALUE = unknown
    VAL_ATTR = utility_location_quality
    DIRECTION = Forward (Source To Destination)
    -> AttributeCreator_22
AttributeCreator_22
    ATTR_TABLE = SET_TO utility_elevation_quality = estimated
    -> AttributeValueMapper
AttributeValueMapper
    SRC = TYPE
    LUT = Primary Distribution,mainLine,Primary Supply,supplyLine,Secondary Distributi,mainLine,Secondary Supply,supplyLine,houseServiceLine,houseServiceLine
    DEFAULT_VALUE = unknown
    VAL_ATTR = utility_class{}
    DIRECTION = Forward (Source To Destination)
    -> AttributeCreator_25
AttributeCreator_25
    ATTR_TABLE = SET_TO utility_function_of_line = flowLine
    -> AttributeFilter_3
AttributeFilter_3
    ATTR_NAME = DIAMETER
    ATTR_VALUES = <Empty>,<Missing>,<Null>,<Unfiltered>,0
    <EMPTY> -> AttributeCreator_26
    <MISSING> -> AttributeCreator_26
    <NULL> -> AttributeCreator_26
    <UNFILTERED> -> AttributeRenamer_28
    0 -> AttributeCreator_26
AttributeRenamer_28
    ATTR_TABLE = RENAME_SET_DEFAULT DIAMETER > utility_exterior_diameter
    -> AttributeCreator_28
Note: using 0 as unknown value
AttributeCreator_26
    ATTR_TABLE = SET_TO utility_exterior_diameter = 0
    -> AttributeCreator_28
AttributeCreator_28
    ATTR_TABLE = SET_TO utility_exterior_diameter_units = cm
    -> RoundPipe (writer CITYGML_1)
    -> roundpipe
