FME workspace nanaimo_electric.fmw

Parameters:
- DestDataset_CITYGML = /media/isaac/Data/_GMCM/Thesis/data/citygml/nanaimo_water_and_electric_network.gml   # Destination CityGML Document
- SourceDataset_ESRISHAPE_5 = /media/isaac/Data/EIFER/Nanaimo_Network_Modeling/data_in/SERVICES_sm.shp   # Source Esri Shapefile(s)
- SourceDataset_ESRISHAPE_6 = /media/isaac/Data/_GMCM/Thesis/data/electric_lines/electric_lines.shp   # Source Esri Shapefile(s)
- SourceDataset_CITYGML = /media/isaac/Data/_GMCM/Thesis/data/citygml/nanaimo_water_network.gml   # Source CityGML File(s)
- SourceDataset_GEOTIFF = /media/isaac/Data/_GMCM/Thesis/data/dem/Nanaimo_DEM1.tif   # Source GeoTIFF File(s)
- SourceDataset_ESRISHAPE = /media/isaac/Data/_GMCM/Thesis/data/digitized/reservoir_no1_cables.shp   # Source Esri Shapefile(s)

Readers:
- ESRISHAPE_1: ESRISHAPE from $(SourceDataset_ESRISHAPE_5)
- ESRISHAPE_2: ESRISHAPE from $(SourceDataset_ESRISHAPE_6)
- CITYGML_1: CITYGML from $(SourceDataset_CITYGML)
- GEOTIFF_1: GEOTIFF from $(SourceDataset_GEOTIFF)
- ESRISHAPE_3: ESRISHAPE from $(SourceDataset_ESRISHAPE)

Writers:
- CITYGML_2: CITYGML to $(DestDataset_CITYGML)

Note: Use the pre-existing TerminalElements / from the water network to make ones / for the electric network. They will both / be related to theie respective buildings / via the connectedCityObject attribute
TerminalElement (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64,
      utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer,
      utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer
    -> TerminalElement (writer CITYGML_2)
    -> AttributeRemover_2
ElectricalMedium (writer CITYGML_2)
    attributes: citygml_target_uri xml_buffer, citygml_feature_role xml_buffer, citygml_feature_role_attr_name xml_buffer, citygml_feature_role_attr_val xml_buffer, gml_description xml_buffer, gml_name xml_buffer, utility_owner xml_buffer, utility_is_classified_by{}.xlink_href xml_buffer, utility_associated_network{}.xlink_href xml_buffer, utility_type xml_char(29), utility_voltage_range xml_buffer, utility_voltage_range_units xml_buffer, utility_amperage_range xml_buffer, utility_amperage_range_units xml_buffer, utility_band_width xml_buffer, utility_band_width_units xml_buffer
Note: Connect nodes with themselves
FeatureMerger_14
    MERGE_TYPE = Attributes Only
    LIST_NAME = _list
    ATTR_CONFLICT_RES = Use Requestor
    CONNECT_Z_MODE = First Wins
    GEOM_TYPE = Build Polygons
    LIST_ATTRS_TO_INCLUDE = _element_index _node_number fme_arc_angle fme_arc_id Node_ID
    REJECT_NULL_MISSING_KEYS = No
    PROCESS_DUPS = Yes
    SUPPLIERS_FIRST = No
    ATTR_ACCUM_MODE = Merge Supplier
    IGNORE_NULLS = No
    JOIN_KEYS = @Value(_node_number) @Value(_node_number) AUTO
    MERGED -> AttributeRenamer_22
Note: Rename Node_ID to / Node_ID_original
AttributeRenamer_22
    ATTR_TABLE = RENAME_SET_DEFAULT Node_ID > Node_ID_original
    -> ListExploder_6
Note: See slides for InterFeatureLinks
ListExploder_6
    INDEX_ATTR = _element_index
    ATTR_ACCUM_MODE = Merge Incoming List
    LIST_ATTR = _list{}
    ATTR_CONFLICT_RES = Use Original
    LIST_FOUND -> AttributeRenamer_23
Note: Rename Node_ID to / Node_ID_merged
AttributeRenamer_23
    ATTR_TABLE = RENAME_SET_DEFAULT Node_ID > Node_ID_merged
    -> TestFilter
Note: Keep only nodes for which / Node_ID_original = Node_ID_merged
TestFilter
    DEFAULT_VALUE = <UNFILTERED>
    TEST_LIST = BOOL_OP,OR,COMPOSITE_TEST,<Unused>,TEST_CLAUSE,"TEST @Value(Node_ID_original) != @Value(Node_ID_merged)",@Value(Node_ID_original) < @Value(Node_ID_merged)
    @Value(Node_ID_original) < @Value(Node_ID_merged) -> TestFilter_2
Note: See slides for / InterFeatureLinks
TestFilter_2
    DEFAULT_VALUE = <UNFILTERED>
    TEST_LIST = BOOL_OP,OR,COMPOSITE_TEST,<Unused>,TEST_CLAUSE,"TEST @Value(Node_ID_original) < @Value(Node_ID_merged)",@Value(Node_ID_original) < @Value(Node_ID_merged)
    @Value(Node_ID_original) < @Value(Node_ID_merged) -> UUIDGenerator_14
Note: Rename Node_ID_original to utility_start_xlink_href / and Node_ID_merged to utility_end_xink_href
AttributeRenamer_24
    ATTR_LIST = Node_ID_original,utility_start_xlink_href,,Node_ID_merged,utility_end_xlink_href,
    -> GeometryRemover_3
    -> AttributeCreator_19
Note: See slides for InterFeatureLinks
GeometryRemover_3 [off]
    -> AttributeCreator_19
Note: Set utility_type = connects
AttributeCreator_19
    ATTR_TABLE = SET_TO utility_type = connects
    -> AttributeCreator_27
Note: Set relationship between InterFeatureLink / and NetworkGraph (+linkMember)
AttributeCreator_27
    ATTR_LIST = citygml_feature_role,linkMember
    -> AttributeRenamer_25
Note: Set gml_id to InterFeatureLink_ID / and gml_parent_id to NetworkGraph_ID
AttributeRenamer_25
    ATTR_LIST = InterFeatureLink_ID,gml_id,,NetworkGraph_ID,gml_parent_id,
    -> StringConcatenator_12
StringConcatenator_12
    PARM_LINE = #@Value(utility_start_xlink_href)
    ACTION = Overwrite Existing Attributes
    ATTRLIST = utility_start_xlink_href
    -> StringConcatenator_11
StringConcatenator_11
    PARM_LINE = #@Value(utility_end_xlink_href)
    ACTION = Overwrite Existing Attributes
    ATTRLIST = utility_end_xlink_href
    -> InterFeatureLink (writer CITYGML_2)
    -> elec_interfeaturelinks
elec_interfeaturelinks: Inspector
TerminalElement (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_role_in_network{}.xlink_href xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer,
      utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer,
      utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer,
      utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29), utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_function xml_buffer, utility_function_codeSpace xml_buffer, utility_usage{} xml_buffer, utility_usage{}.codeSpace xml_buffer, utility_connected_city_object xml_buffer, utility_year_of_construction xml_date, utility_status xml_char(16),
      utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer
terminalelement_node: Inspector
terminalelement_interfeaturelink: Inspector
Cable: Inspector
Cable (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer,
      utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer,
      utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer, utility_function_of_line xml_buffer, utility_function_of_line_codeSpace xml_buffer, utility_is_transmission xml_boolean, utility_is_communication xml_boolean, utility_cross_section xml_real64, utility_cross_section_units xml_buffer
Network (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64,
      utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer,
      utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, utility_class xml_buffer, utility_class_codeSpace xml_buffer, utility_function{} xml_buffer, utility_function{}.codeSpace xml_buffer, utility_usage{} xml_buffer, utility_usage{}.codeSpace xml_buffer,
      utility_transported_medium_xlink_href xml_buffer, utility_sub_network{}.xlink_href xml_buffer, utility_topo_graph_xlink_href xml_buffer, utility_component{}.xlink_href xml_buffer, utility_supplies_xlink_href xml_buffer, utility_sub_ordinate_network{}.xlink_href xml_buffer, utility_super_ordinate_network{}.xlink_href xml_buffer
    -> Network (writer CITYGML_2)
Network (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_role_in_network{}.xlink_href xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer,
      utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer,
      utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer,
      utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29), utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_class xml_buffer, utility_class_codeSpace xml_buffer, utility_function{} xml_buffer, utility_function{}.codeSpace xml_buffer, utility_usage{} xml_buffer, utility_usage{}.codeSpace xml_buffer, utility_transported_medium_xlink_href xml_buffer,
      utility_sub_network{}.xlink_href xml_buffer, utility_topo_graph_xlink_href xml_buffer, utility_component{}.xlink_href xml_buffer, utility_supplies_xlink_href xml_buffer, utility_sub_ordinate_network{}.xlink_href xml_buffer, utility_super_ordinate_network{}.xlink_href xml_buffer
NetworkGraph (reader CITYGML_1)
    attributes: citygml_target_uri xml_buffer, citygml_feature_role xml_buffer, citygml_feature_role_attr_name xml_buffer, citygml_feature_role_attr_val xml_buffer, gml_description xml_buffer, gml_name xml_buffer, utility_feature_graph_member{}.xlink_href xml_buffer, utility_link_member{}.xlink_href xml_buffer
    -> NetworkGraph (writer CITYGML_2)
NetworkGraph (writer CITYGML_2)
    attributes: citygml_target_uri xml_buffer, citygml_feature_role xml_buffer, citygml_feature_role_attr_name xml_buffer, citygml_feature_role_attr_val xml_buffer, gml_description xml_buffer, gml_name xml_buffer, utility_feature_graph_member{}.xlink_href xml_buffer, utility_link_member{}.xlink_href xml_buffer, utility_network_link_member{}.xlink_href xml_buffer
RoundPipe: Inspector
Building: Inspector
ExteriorMaterial (reader CITYGML_1)
    attributes: citygml_target_uri xml_buffer, citygml_feature_role xml_buffer, citygml_feature_role_attr_name xml_buffer, citygml_feature_role_attr_val xml_buffer, gml_description xml_buffer, gml_name xml_buffer, utility_type xml_buffer, utility_type_codeSpace xml_buffer, utility_consists_of_fm{}.xlink_href xml_buffer, utility_consists_of{}.xlink_href xml_buffer, utility_is_classified_by{}.xlink_href xml_buffer, utility_used_by{}.xlink_href xml_buffer
    -> ExteriorMaterial (writer CITYGML_2)
ExteriorMaterial (writer CITYGML_2)
    attributes: citygml_target_uri xml_buffer, citygml_feature_role xml_buffer, citygml_feature_role_attr_name xml_buffer, citygml_feature_role_attr_val xml_buffer, gml_description xml_buffer, gml_name xml_buffer, utility_type xml_buffer, utility_type_codeSpace xml_buffer, utility_consists_of_fm{}.xlink_href xml_buffer, utility_consists_of{}.xlink_href xml_buffer, utility_is_classified_by{}.xlink_href xml_buffer, utility_used_by{}.xlink_href xml_buffer
FeatureGraph (reader CITYGML_1)
    attributes: citygml_target_uri xml_buffer, citygml_feature_role xml_buffer, citygml_feature_role_attr_name xml_buffer, citygml_feature_role_attr_val xml_buffer, gml_description xml_buffer, gml_name xml_buffer, utility_link_member{}.xlink_href xml_buffer, utility_node_member{}.xlink_href xml_buffer, utility_network_link_member{}.xlink_href xml_buffer
    -> FeatureGraph (writer CITYGML_2)
FeatureGraph (writer CITYGML_2)
    attributes: citygml_target_uri xml_buffer, citygml_feature_role xml_buffer, citygml_feature_role_attr_name xml_buffer, citygml_feature_role_attr_val xml_buffer, gml_description xml_buffer, gml_name xml_buffer, utility_link_member{}.xlink_href xml_buffer, utility_node_member{}.xlink_href xml_buffer
InteriorFeatureLink (reader CITYGML_1)
    attributes: citygml_target_uri xml_buffer, citygml_feature_role xml_buffer, citygml_feature_role_attr_name xml_buffer, citygml_feature_role_attr_val xml_buffer, gml_description xml_buffer, gml_name xml_buffer, utility_direction xml_char(1), utility_link_control xml_xml, utility_start_xlink_href xml_buffer, utility_end_xlink_href xml_buffer
    -> InteriorFeatureLink (writer CITYGML_2)
InteriorFeatureLink (writer CITYGML_2)
    attributes: citygml_target_uri xml_buffer, citygml_feature_role xml_buffer, citygml_feature_role_attr_name xml_buffer, citygml_feature_role_attr_val xml_buffer, gml_description xml_buffer, gml_name xml_buffer, utility_direction xml_char(1), utility_link_control xml_xml, utility_start_xlink_href xml_buffer, utility_end_xlink_href xml_buffer
Node (reader CITYGML_1)
    attributes: citygml_target_uri xml_buffer, citygml_feature_role xml_buffer, citygml_feature_role_attr_name xml_buffer, citygml_feature_role_attr_val xml_buffer, gml_description xml_buffer, gml_name xml_buffer, utility_type xml_char(8), utility_connection_signature xml_xml, utility_link_control xml_xml
    -> Node (writer CITYGML_2)
Node (writer CITYGML_2)
    attributes: citygml_target_uri xml_buffer, citygml_feature_role xml_buffer, citygml_feature_role_attr_name xml_buffer, citygml_feature_role_attr_val xml_buffer, gml_description xml_buffer, gml_name xml_buffer, utility_type xml_char(8), utility_connection_signature xml_xml, utility_link_control xml_xml
InterFeatureLink (reader CITYGML_1)
    attributes: citygml_target_uri xml_buffer, citygml_feature_role xml_buffer, citygml_feature_role_attr_name xml_buffer, citygml_feature_role_attr_val xml_buffer, gml_description xml_buffer, gml_name xml_buffer, utility_direction xml_char(1), utility_link_control xml_xml, utility_start_xlink_href xml_buffer, utility_end_xlink_href xml_buffer, utility_type xml_char(8)
    -> InterFeatureLink (writer CITYGML_2)
InterFeatureLink (writer CITYGML_2)
    attributes: citygml_target_uri xml_buffer, citygml_feature_role xml_buffer, citygml_feature_role_attr_name xml_buffer, citygml_feature_role_attr_val xml_buffer, gml_description xml_buffer, gml_name xml_buffer, utility_direction xml_char(1), utility_link_control xml_xml, utility_start_xlink_href xml_buffer, utility_end_xlink_href xml_buffer, utility_type xml_char(8)

Bookmark: Read source data, remap attributes and build topology
electric_lines (reader ESRISHAPE_2)
    attributes: id long, type char(254)
    -> FeatureMerger_8 [REQUESTOR]
reservoir_no1_cables (reader ESRISHAPE_3)
    attributes: id long
    -> FeatureMerger_8 [REQUESTOR]
FeatureMerger_8
    MERGE_TYPE = Attributes Only
    ATTR_CONFLICT_RES = Use Requestor
    REJECT_NULL_MISSING_KEYS = No
    PROCESS_DUPS = No
    SUPPLIERS_FIRST = No
    ATTR_ACCUM_MODE = Merge Supplier
    IGNORE_NULLS = No
    JOIN_KEYS = 1 1 AUTO
    MERGED -> SmartCleaner_2013
Note: Without this custom transformer, / the TopologyBuilder will not properly / break up the lines into individual / edges
SmartCleaner_2013
    VAL = 1
    LEN = 1
    CLEANED -> TopologyBuilder
TopologyBuilder
    OVERLAPPING_MODE = No
    MAX = 0
    DEAGGREGATE_INPUT = Yes
    BOUNDING_EDGES = All
    CLEAN_DATA = No
    PROP_ATTRS = No
    ALLOW_CYCLES = No
    NODE -> FeatureMerger [REQUESTOR]
    LINE -> SurfaceDraper [DRAPE_FEATURES]

Bookmark: Electrical TerminalElements
Note: Remove most of the attributes, / we are going to redefine them
Note: Add necessary IDs
AttributeRemover_2
    REMOVE_ATTRS = utility_medium_supply{0}.utility_optical_medium_supply_utility_storage{0}.utility_storage_utility_type,utility_medium_supply{0}.utility_optical_medium_supply_utility_storage{0}.utility_storage_utility_inflow_rate_units,externalReference{0}.externalObject.uri,utility_medium_supply{0}.utility_liquid_medium_supply_utility_storage{0}.utility_storage_utility_outflow_rate_units,citygml_feature_role_attr_name,utility_medium_supply{0}.utility_abstract_medium_supply_utility_storage{0}.utility_storage_utility_max_capacity,utility_medium_supply{0}.utility_electrical_medium_supply_utility_potential_supply_utility_supply_utility_flow_rate_units,utility_medium_supply{0}.utility_liquid_medium_supply_utility_potential_supply_utility_supply_utility_flow_rate,utility_medium_supply{0}.utility_optical_medium_supply_utility_storage{0}.utility_storage_utility_inflow_rate,utility_medium_supply{0}.utility_gaseous_medium_supply_utility_storage{0}.utility_storage_utility_fill_level,gml_name,utility_medium_supply{0}.utility_electrical_medium_supply_utility_potential_supply_utility_supply_utility_flow_rate,utility_medium_supply{0}.utility_liquid_medium_supply_utility_type_codeSpace,utility_medium_supply{0}.utility_electrical_medium_supply_utility_storage{0}.utility_storage_utility_type,utility_medium_supply{0}.utility_gaseous_medium_supply_utility_potential_supply_utility_supply_utility_flow_rate_units,utility_medium_supply{0}.utility_optical_medium_supply_utility_storage{0}.utility_storage_utility_max_capacity,utility_medium_supply{0}.utility_solid_medium_supply_utility_storage{0}.utility_storage_utility_fill_level,gml_description,utility_medium_supply{0}.utility_gaseous_medium_supply_utility_storage{0}.utility_storage_utility_inflow_rate,utility_medium_supply{0}.utility_liquid_medium_supply_utility_storage{0}.utility_storage_utility_max_capacity_units,utility_medium_supply{0}.utility_solid_medium_supply_utility_storage{0}.utility_storage_utility_outflow_rate,utility_medium_supply{0}.utility_optical_medium_supply_utility_current_supply_utility_supply_utility_status,utility_medium_supply{0}.utility_abstract_medium_supply_utility_storage{0}.utility_storage_utility_type,utility_location_quality,utility_medium_supply{0}.utility_optical_medium_supply_utility_storage{0}.utility_storage_utility_outflow_rate_units,utility_medium_supply{0}.utility_gaseous_medium_supply_utility_current_supply_utility_supply_utility_flow_rate,utility_function,utility_medium_supply{0}.utility_solid_medium_supply_utility_current_supply_utility_supply_utility_flow_rate_units,utility_medium_supply{0}.utility_liquid_medium_supply_utility_storage{0}.utility_storage_utility_outflow_rate,citygml_feature_role_attr_val,citygml_generalizes_to{0}.xlink_href,utility_medium_supply{0}.utility_electrical_medium_supply_utility_current_supply_utility_supply_utility_flow_rate_units,utility_medium_supply{0}.utility_electrical_medium_supply_utility_storage{0}.utility_storage_utility_fill_level,utility_medium_supply{0}.utility_liquid_medium_supply_utility_storage{0}.utility_storage_utility_inflow_rate_units,utility_medium_supply{0}.utility_optical_medium_supply_utility_potential_supply_utility_supply_utility_status,utility_medium_supply{0}.utility_solid_medium_supply_utility_potential_supply_utility_supply_utility_status,utility_medium_supply{0}.utility_abstract_medium_supply_utility_current_supply_utility_supply_utility_flow_rate_units,utility_medium_supply{0}.utility_abstract_medium_supply_utility_storage{0}.utility_storage_utility_max_capacity_units,utility_medium_supply{0}.utility_liquid_medium_supply_utility_storage{0}.utility_storage_utility_inflow_rate,utility_function_codeSpace,utility_medium_supply{0}.utility_electrical_medium_supply_utility_storage{0}.utility_storage_utility_inflow_rate_units,utility_medium_supply{0}.utility_electrical_medium_supply_utility_storage{0}.utility_storage_utility_outflow_rate_units,utility_medium_supply{0}.utility_abstract_medium_supply_utility_storage{0}.utility_storage_utility_fill_level,utility_medium_supply{0}.utility_liquid_medium_supply_utility_storage{0}.utility_storage_utility_fill_level,utility_medium_supply{0}.utility_optical_medium_supply_utility_storage{0}.utility_storage_utility_outflow_rate,citygml_appearance{0}.xlink_href,utility_medium_supply{0}.utility_liquid_medium_supply_utility_current_supply_utility_supply_utility_status,utility_medium_supply{0}.utility_optical_medium_supply_utility_current_supply_utility_supply_utility_flow_rate_units,utility_medium_supply{0}.utility_gaseous_medium_supply_utility_type,utility_year_of_construction,utility_consists_of{0}.xlink_href,utility_medium_supply{0}.utility_abstract_medium_supply_utility_storage{0}.utility_storage_utility_type_codeSpace,utility_medium_supply{0}.utility_gaseous_medium_supply_utility_storage{0}.utility_storage_utility_type,citygml_creationDate,utility_medium_supply{0}.utility_optical_medium_supply_utility_current_supply_utility_supply_utility_flow_rate,utility_occupied_hollow_space_xlink_href,utility_topo_graph_xlink_href,utility_medium_supply{0}.utility_optical_medium_supply_utility_storage{0}.utility_storage_utility_type_codeSpace,utility_medium_supply{0}.utility_solid_medium_supply_utility_type,utility_medium_supply{0}.utility_electrical_medium_supply_utility_current_supply_utility_supply_utility_flow_rate,utility_medium_supply{0}.utility_gaseous_medium_supply_utility_storage{0}.utility_storage_utility_max_capacity,utility_medium_supply{0}.utility_liquid_medium_supply_utility_current_supply_utility_supply_utility_flow_rate,utility_medium_supply{0}.utility_solid_medium_supply_utility_storage{0}.utility_storage_utility_type_codeSpace,utility_medium_supply{0}.utility_liquid_medium_supply_utility_storage{0}.utility_storage_utility_max_capacity,utility_medium_supply{0}.utility_gaseous_medium_supply_utility_current_supply_utility_supply_utility_flow_rate_units,gml_parent_id,utility_medium_supply{0}.utility_solid_medium_supply_utility_storage{0}.utility_storage_utility_max_capacity,citygml_terminationDate,utility_medium_supply{0}.utility_liquid_medium_supply_utility_current_supply_utility_supply_utility_flow_rate_units,utility_role_in_network{0}.xlink_href,utility_medium_supply{0}.utility_abstract_medium_supply_utility_potential_supply_utility_supply_utility_flow_rate,utility_medium_supply{0}.utility_solid_medium_supply_utility_storage{0}.utility_storage_utility_max_capacity_units,utility_medium_supply{0}.utility_abstract_medium_supply_utility_storage{0}.utility_storage_utility_outflow_rate_units,utility_medium_supply{0}.utility_liquid_medium_supply_utility_potential_supply_utility_supply_utility_status,utility_elevation_quality,utility_medium_supply{0}.utility_abstract_medium_supply_utility_potential_supply_utility_supply_utility_flow_rate_units,utility_medium_supply{0}.utility_electrical_medium_supply_utility_storage{0}.utility_storage_utility_max_capacity,utility_medium_supply{0}.utility_electrical_medium_supply_utility_type,utility_medium_supply{0}.utility_abstract_medium_supply_utility_potential_supply_utility_supply_utility_status,utility_medium_supply{0}.utility_gaseous_medium_supply_utility_storage{0}.utility_storage_utility_inflow_rate_units,utility_medium_supply{0}.utility_gaseous_medium_supply_utility_storage{0}.utility_storage_utility_max_capacity_units,utility_medium_supply{0}.utility_gaseous_medium_supply_utility_storage{0}.utility_storage_utility_type_codeSpace,utility_medium_supply{0}.utility_gaseous_medium_supply_utility_potential_supply_utility_supply_utility_status,utility_class,utility_class_codeSpace,utility_medium_supply{0}.utility_abstract_medium_supply_utility_storage{0}.utility_storage_utility_outflow_rate,utility_medium_supply{0}.utility_optical_medium_supply_utility_potential_supply_utility_supply_utility_flow_rate,externalReference{0}.externalObject.name,utility_status,citygml_relative_to_water,citygml_target_uri,utility_medium_supply{0}.utility_electrical_medium_supply_utility_current_supply_utility_supply_utility_status,utility_medium_supply{0}.utility_liquid_medium_supply_utility_potential_supply_utility_supply_utility_flow_rate_units,gml_id,utility_medium_supply{0}.utility_electrical_medium_supply_utility_storage{0}.utility_storage_utility_max_capacity_units,utility_medium_supply{0}.utility_electrical_medium_supply_utility_storage{0}.utility_storage_utility_type_codeSpace,utility_medium_supply{0}.utility_gaseous_medium_supply_utility_potential_supply_utility_supply_utility_flow_rate,utility_medium_supply{0}.utility_liquid_medium_supply_utility_storage{0}.utility_storage_utility_type_codeSpace,utility_medium_supply{0}.utility_electrical_medium_supply_utility_potential_supply_utility_supply_utility_status,utility_medium_supply{0}.utility_electrical_medium_supply_utility_storage{0}.utility_storage_utility_inflow_rate,utility_medium_supply{0}.utility_gaseous_medium_supply_utility_storage{0}.utility_storage_utility_outflow_rate,utility_medium_supply{0}.utility_optical_medium_supply_utility_type,utility_medium_supply{0}.utility_optical_medium_supply_utility_potential_supply_utility_supply_utility_flow_rate_units,utility_medium_supply{0}.utility_optical_medium_supply_utility_storage{0}.utility_storage_utility_fill_level,utility_medium_supply{0}.utility_solid_medium_supply_utility_storage{0}.utility_storage_utility_inflow_rate,utility_medium_supply{0}.utility_liquid_medium_supply_utility_type,citygml_feature_role,utility_has_material{0}.xlink_href,utility_medium_supply{0}.utility_abstract_medium_supply_utility_storage{0}.utility_storage_utility_inflow_rate,utility_medium_supply{0}.utility_electrical_medium_supply_utility_storage{0}.utility_storage_utility_outflow_rate,utility_medium_supply{0}.utility_gaseous_medium_supply_utility_type_codeSpace,utility_medium_supply{0}.utility_solid_medium_supply_utility_type_codeSpace,utility_medium_supply{0}.utility_solid_medium_supply_utility_storage{0}.utility_storage_utility_type,utility_medium_supply{0}.utility_abstract_medium_supply_utility_storage{0}.utility_storage_utility_inflow_rate_units,utility_medium_supply{0}.utility_solid_medium_supply_utility_potential_supply_utility_supply_utility_flow_rate_units,utility_medium_supply{0}.utility_solid_medium_supply_utility_storage{0}.utility_storage_utility_inflow_rate_units,utility_medium_supply{0}.utility_gaseous_medium_supply_utility_storage{0}.utility_storage_utility_outflow_rate_units,utility_medium_supply{0}.utility_solid_medium_supply_utility_potential_supply_utility_supply_utility_flow_rate,citygml_level_of_detail{0},utility_medium_supply{0}.utility_solid_medium_supply_utility_current_supply_utility_supply_utility_flow_rate,utility_medium_supply{0}.utility_abstract_medium_supply_utility_current_supply_utility_supply_utility_flow_rate,utility_medium_supply{0}.utility_liquid_medium_supply_utility_storage{0}.utility_storage_utility_type,utility_medium_supply{0}.utility_solid_medium_supply_utility_storage{0}.utility_storage_utility_outflow_rate_units,utility_medium_supply{0}.utility_abstract_medium_supply_utility_current_supply_utility_supply_utility_status,utility_medium_supply{0}.utility_optical_medium_supply_utility_storage{0}.utility_storage_utility_max_capacity_units,citygml_relative_to_terrain,utility_usage{0}.codeSpace,externalReference{0}.informationSystem,utility_medium_supply{0}.utility_gaseous_medium_supply_utility_current_supply_utility_supply_utility_status,utility_medium_supply{0}.utility_solid_medium_supply_utility_current_supply_utility_supply_utility_status
    LIST_ATTRS = citygml_appearance{} citygml_appearance{}.xlink_href citygml_generalizes_to{} citygml_generalizes_to{}.xlink_href citygml_level_of_detail{} externalReference{} externalReference{}.externalObject.name externalReference{}.externalObject.uri externalReference{}.informationSystem utility_consists_of{} utility_consists_of{}.xlink_href utility_has_material{} utility_has_material{}.xlink_href utility_medium_supply{} utility_medium_supply{}.utility_abstract_medium_supply_utility_current_supply_utility_supply_utility_flow_rate utility_medium_supply{}.utility_abstract_medium_supply_utility_current_supply_utility_supply_utility_flow_rate_units utility_medium_supply{}.utility_abstract_medium_supply_utility_current_supply_utility_supply_utility_status utility_medium_supply{}.utility_abstract_medium_supply_utility_potential_supply_utility_supply_utility_flow_rate utility_medium_supply{}.utility_abstract_medium_supply_utility_potential_supply_utility_supply_utility_flow_rate_units utility_medium_supply{}.utility_abstract_medium_supply_utility_potential_supply_utility_supply_utility_status utility_medium_supply{}.utility_abstract_medium_supply_utility_storage{} utility_medium_supply{}.utility_abstract_medium_supply_utility_storage{}.utility_storage_utility_fill_level utility_medium_supply{}.utility_abstract_medium_supply_utility_storage{}.utility_storage_utility_inflow_rate utility_medium_supply{}.utility_abstract_medium_supply_utility_storage{}.utility_storage_utility_inflow_rate_units utility_medium_supply{}.utility_abstract_medium_supply_utility_storage{}.utility_storage_utility_max_capacity utility_medium_supply{}.utility_abstract_medium_supply_utility_storage{}.utility_storage_utility_max_capacity_units utility_medium_supply{}.utility_abstract_medium_supply_utility_storage{}.utility_storage_utility_outflow_rate utility_medium_supply{}.utility_abstract_medium_supply_utility_storage{}.utility_storage_utility_outflow_rate_units utility_medium_supply{}.utility_abstract_medium_supply_utility_storage{}.utility_storage_utility_type utility_medium_supply{}.utility_abstract_medium_supply_utility_storage{}.utility_storage_utility_type_codeSpace utility_medium_supply{}.utility_electrical_medium_supply_utility_current_supply_utility_supply_utility_flow_rate utility_medium_supply{}.utility_electrical_medium_supply_utility_current_supply_utility_supply_utility_flow_rate_units utility_medium_supply{}.utility_electrical_medium_supply_utility_current_supply_utility_supply_utility_status utility_medium_supply{}.utility_electrical_medium_supply_utility_potential_supply_utility_supply_utility_flow_rate utility_medium_supply{}.utility_electrical_medium_supply_utility_potential_supply_utility_supply_utility_flow_rate_units utility_medium_supply{}.utility_electrical_medium_supply_utility_potential_supply_utility_supply_utility_status utility_medium_supply{}.utility_electrical_medium_supply_utility_storage{} utility_medium_supply{}.utility_electrical_medium_supply_utility_storage{}.utility_storage_utility_fill_level utility_medium_supply{}.utility_electrical_medium_supply_utility_storage{}.utility_storage_utility_inflow_rate utility_medium_supply{}.utility_electrical_medium_supply_utility_storage{}.utility_storage_utility_inflow_rate_units utility_medium_supply{}.utility_electrical_medium_supply_utility_storage{}.utility_storage_utility_max_capacity utility_medium_supply{}.utility_electrical_medium_supply_utility_storage{}.utility_storage_utility_max_capacity_units utility_medium_supply{}.utility_electrical_medium_supply_utility_storage{}.utility_storage_utility_outflow_rate utility_medium_supply{}.utility_electrical_medium_supply_utility_storage{}.utility_storage_utility_outflow_rate_units utility_medium_supply{}.utility_electrical_medium_supply_utility_storage{}.utility_storage_utility_type utility_medium_supply{}.utility_electrical_medium_supply_utility_storage{}.utility_storage_utility_type_codeSpace utility_medium_supply{}.utility_electrical_medium_supply_utility_type utility_medium_supply{}.utility_gaseous_medium_supply_utility_current_supply_utility_supply_utility_flow_rate utility_medium_supply{}.utility_gaseous_medium_supply_utility_current_supply_utility_supply_utility_flow_rate_units utility_medium_supply{}.utility_gaseous_medium_supply_utility_current_supply_utility_supply_utility_status utility_medium_supply{}.utility_gaseous_medium_supply_utility_potential_supply_utility_supply_utility_flow_rate utility_medium_supply{}.utility_gaseous_medium_supply_utility_potential_supply_utility_supply_utility_flow_rate_units utility_medium_supply{}.utility_gaseous_medium_supply_utility_potential_supply_utility_supply_utility_status utility_medium_supply{}.utility_gaseous_medium_supply_utility_storage{} utility_medium_supply{}.utility_gaseous_medium_supply_utility_storage{}.utility_storage_utility_fill_level utility_medium_supply{}.utility_gaseous_medium_supply_utility_storage{}.utility_storage_utility_inflow_rate utility_medium_supply{}.utility_gaseous_medium_supply_utility_storage{}.utility_storage_utility_inflow_rate_units utility_medium_supply{}.utility_gaseous_medium_supply_utility_storage{}.utility_storage_utility_max_capacity utility_medium_supply{}.utility_gaseous_medium_supply_utility_storage{}.utility_storage_utility_max_capacity_units utility_medium_supply{}.utility_gaseous_medium_supply_utility_storage{}.utility_storage_utility_outflow_rate utility_medium_supply{}.utility_gaseous_medium_supply_utility_storage{}.utility_storage_utility_outflow_rate_units utility_medium_supply{}.utility_gaseous_medium_supply_utility_storage{}.utility_storage_utility_type utility_medium_supply{}.utility_gaseous_medium_supply_utility_storage{}.utility_storage_utility_type_codeSpace utility_medium_supply{}.utility_gaseous_medium_supply_utility_type utility_medium_supply{}.utility_gaseous_medium_supply_utility_type_codeSpace utility_medium_supply{}.utility_liquid_medium_supply_utility_current_supply_utility_supply_utility_flow_rate utility_medium_supply{}.utility_liquid_medium_supply_utility_current_supply_utility_supply_utility_flow_rate_units utility_medium_supply{}.utility_liquid_medium_supply_utility_current_supply_utility_supply_utility_status utility_medium_supply{}.utility_liquid_medium_supply_utility_potential_supply_utility_supply_utility_flow_rate utility_medium_supply{}.utility_liquid_medium_supply_utility_potential_supply_utility_supply_utility_flow_rate_units utility_medium_supply{}.utility_liquid_medium_supply_utility_potential_supply_utility_supply_utility_status utility_medium_supply{}.utility_liquid_medium_supply_utility_storage{} utility_medium_supply{}.utility_liquid_medium_supply_utility_storage{}.utility_storage_utility_fill_level utility_medium_supply{}.utility_liquid_medium_supply_utility_storage{}.utility_storage_utility_inflow_rate utility_medium_supply{}.utility_liquid_medium_supply_utility_storage{}.utility_storage_utility_inflow_rate_units utility_medium_supply{}.utility_liquid_medium_supply_utility_storage{}.utility_storage_utility_max_capacity utility_medium_supply{}.utility_liquid_medium_supply_utility_storage{}.utility_storage_utility_max_capacity_units utility_medium_supply{}.utility_liquid_medium_supply_utility_storage{}.utility_storage_utility_outflow_rate utility_medium_supply{}.utility_liquid_medium_supply_utility_storage{}.utility_storage_utility_outflow_rate_units utility_medium_supply{}.utility_liquid_medium_supply_utility_storage{}.utility_storage_utility_type utility_medium_supply{}.utility_liquid_medium_supply_utility_storage{}.utility_storage_utility_type_codeSpace utility_medium_supply{}.utility_liquid_medium_supply_utility_type utility_medium_supply{}.utility_liquid_medium_supply_utility_type_codeSpace utility_medium_supply{}.utility_optical_medium_supply_utility_current_supply_utility_supply_utility_flow_rate utility_medium_supply{}.utility_optical_medium_supply_utility_current_supply_utility_supply_utility_flow_rate_units utility_medium_supply{}.utility_optical_medium_supply_utility_current_supply_utility_supply_utility_status utility_medium_supply{}.utility_optical_medium_supply_utility_potential_supply_utility_supply_utility_flow_rate utility_medium_supply{}.utility_optical_medium_supply_utility_potential_supply_utility_supply_utility_flow_rate_units utility_medium_supply{}.utility_optical_medium_supply_utility_potential_supply_utility_supply_utility_status utility_medium_supply{}.utility_optical_medium_supply_utility_storage{} utility_medium_supply{}.utility_optical_medium_supply_utility_storage{}.utility_storage_utility_fill_level utility_medium_supply{}.utility_optical_medium_supply_utility_storage{}.utility_storage_utility_inflow_rate utility_medium_supply{}.utility_optical_medium_supply_utility_storage{}.utility_storage_utility_inflow_rate_units utility_medium_supply{}.utility_optical_medium_supply_utility_storage{}.utility_storage_utility_max_capacity utility_medium_supply{}.utility_optical_medium_supply_utility_storage{}.utility_storage_utility_max_capacity_units utility_medium_supply{}.utility_optical_medium_supply_utility_storage{}.utility_storage_utility_outflow_rate utility_medium_supply{}.utility_optical_medium_supply_utility_storage{}.utility_storage_utility_outflow_rate_units utility_medium_supply{}.utility_optical_medium_supply_utility_storage{}.utility_storage_utility_type utility_medium_supply{}.utility_optical_medium_supply_utility_storage{}.utility_storage_utility_type_codeSpace utility_medium_supply{}.utility_optical_medium_supply_utility_type utility_medium_supply{}.utility_solid_medium_supply_utility_current_supply_utility_supply_utility_flow_rate utility_medium_supply{}.utility_solid_medium_supply_utility_current_supply_utility_supply_utility_flow_rate_units utility_medium_supply{}.utility_solid_medium_supply_utility_current_supply_utility_supply_utility_status utility_medium_supply{}.utility_solid_medium_supply_utility_potential_supply_utility_supply_utility_flow_rate utility_medium_supply{}.utility_solid_medium_supply_utility_potential_supply_utility_supply_utility_flow_rate_units utility_medium_supply{}.utility_solid_medium_supply_utility_potential_supply_utility_supply_utility_status utility_medium_supply{}.utility_solid_medium_supply_utility_storage{} utility_medium_supply{}.utility_solid_medium_supply_utility_storage{}.utility_storage_utility_fill_level utility_medium_supply{}.utility_solid_medium_supply_utility_storage{}.utility_storage_utility_inflow_rate utility_medium_supply{}.utility_solid_medium_supply_utility_storage{}.utility_storage_utility_inflow_rate_units utility_medium_supply{}.utility_solid_medium_supply_utility_storage{}.utility_storage_utility_max_capacity utility_medium_supply{}.utility_solid_medium_supply_utility_storage{}.utility_storage_utility_max_capacity_units utility_medium_supply{}.utility_solid_medium_supply_utility_storage{}.utility_storage_utility_outflow_rate utility_medium_supply{}.utility_solid_medium_supply_utility_storage{}.utility_storage_utility_outflow_rate_units utility_medium_supply{}.utility_solid_medium_supply_utility_storage{}.utility_storage_utility_type utility_medium_supply{}.utility_solid_medium_supply_utility_storage{}.utility_storage_utility_type_codeSpace utility_medium_supply{}.utility_solid_medium_supply_utility_type utility_medium_supply{}.utility_solid_medium_supply_utility_type_codeSpace utility_role_in_network{} utility_role_in_network{}.xlink_href utility_usage{} utility_usage{}.codeSpace
    -> UUIDGenerator_9
Note: Merge with Network & / NetworkGraph
FeatureMerger_2
    MERGE_TYPE = Attributes Only
    ATTR_CONFLICT_RES = Use Requestor
    REJECT_NULL_MISSING_KEYS = No
    PROCESS_DUPS = No
    SUPPLIERS_FIRST = No
    ATTR_ACCUM_MODE = Merge Supplier
    IGNORE_NULLS = No
    JOIN_KEYS = 1 1 AUTO
    MERGED -> AttributeCreator_31
    MERGED -> SpatialRelator [Requestor]

Bookmark: TerminalElement ID (electric)
UUIDGenerator_9
    UUID_ATTR = ElectricalTerminalElementID
    -> StringConcatenator_9
StringConcatenator_9
    PARM_LINE = TerminalElementID_@Value(ElectricalTerminalElementID)
    ACTION = Overwrite Existing Attributes
    ATTRLIST = ElectricalTerminalElementID
    -> UUIDGenerator_17

Bookmark: Node ID
UUIDGenerator_17
    UUID_ATTR = Node_ID
    -> StringConcatenator_10
StringConcatenator_10
    PARM_LINE = NodeID_@Value(Node_ID)
    ACTION = Overwrite Existing Attributes
    ATTRLIST = Node_ID
    -> UUIDGenerator_18

Bookmark: FeatureGraph ID
UUIDGenerator_18
    UUID_ATTR = FeatureGraph_ID
    -> StringConcatenator_23
StringConcatenator_23
    PARM_LINE = FeatureGraphID_@Value(FeatureGraph_ID)
    ACTION = Overwrite Existing Attributes
    ATTRLIST = FeatureGraph_ID
    -> UUIDGenerator_19

Bookmark: InterFeatureLink ID
UUIDGenerator_19
    UUID_ATTR = InterFeatureLink_ID
    -> StringConcatenator_24
StringConcatenator_24
    PARM_LINE = InterFeatureLinkID_@Value(InterFeatureLink_ID)
    ACTION = Overwrite Existing Attributes
    ATTRLIST = InterFeatureLink_ID
    -> FeatureMerger_2 [REQUESTOR]

Bookmark: Create Network, NetworkGraph & LiquidMedium
Note: The NetworkID and NetworkGraphID are needed in lots of other places in the workbench. These connections go to a series of FeatureMergers to deliver the IDs where needed.
Creator_3
    NUM = 1
    GEOMTYPE = Geometry Object
    CREATED -> UUIDGenerator_2
Note: Set function, usage & name
AttributeCreator_5
    ATTR_TABLE:
      SET_TO utility_usage{0} = distribution
      SET_TO utility_function{0} = distribution
      SET_TO gml_name = Electric Network
    -> AttributeRenamer_3
Note: Set the network ID as the gml_id / Also set the transportedMedium to be the LiquidMedium ID
AttributeRenamer_3
    ATTR_TABLE = RENAME_SET_DEFAULT Network_ID > gml_id
    -> Network (writer CITYGML_2)
Note: Set feature role as transportedMedium. / Also set transportedMedium to be freshWater + its properties
AttributeCreator_9
    ATTR_TABLE:
      SET_TO citygml_feature_role = transportedMedium
      SET_TO utility_type = singlePhaseAlternatingCurrent
    -> AttributeRenamer_10
Note: Set LiquidMedium ID as gml_id / Also set NetworkID as parent_gml_id
AttributeRenamer_10
    ATTR_TABLE:
      RENAME_SET_DEFAULT ElectricalMedium_ID > gml_id
      RENAME_SET_DEFAULT Network_ID > gml_parent_id
    -> ElectricalMedium (writer CITYGML_2)
Note: Set relationship between Network / and NetworkGraph (+topoGraph)
AttributeCreator_24
    ATTR_TABLE = SET_TO citygml_feature_role = topoGraph
    -> AttributeRenamer_2
Note: Set gml_id as NetworkGraph_ID / and gml_parent_id as NetworkGraph_ID
AttributeRenamer_2
    ATTR_TABLE:
      RENAME_SET_DEFAULT NetworkGraph_ID > gml_id
      RENAME_SET_DEFAULT Network_ID > gml_parent_id
    -> NetworkGraph (writer CITYGML_2)

Bookmark: Network ID
UUIDGenerator_2
    UUID_ATTR = Network_ID
    -> StringConcatenator_2
StringConcatenator_2
    PARM_LINE = NetworkID_@Value(Network_ID)
    ACTION = Overwrite Existing Attributes
    ATTRLIST = Network_ID
    -> UUIDGenerator_3

Bookmark: NetworkGraph ID
UUIDGenerator_3
    UUID_ATTR = NetworkGraph_ID
    -> StringConcatenator_3
StringConcatenator_3
    PARM_LINE = NetworkGraphID_@Value(NetworkGraph_ID)
    ACTION = Overwrite Existing Attributes
    ATTRLIST = NetworkGraph_ID
    -> UUIDGenerator_7
    -> FeatureMerger_8 [SUPPLIER]
    -> FeatureMerger [SUPPLIER]
    -> FeatureMerger_2 [SUPPLIER]

Bookmark: LiquidMedium ID
UUIDGenerator_7
    UUID_ATTR = ElectricalMedium_ID
    -> StringConcatenator_7
StringConcatenator_7
    PARM_LINE = ElectricalMediumID_@Value(ElectricalMedium_ID)
    ACTION = Overwrite Existing Attributes
    ATTRLIST = ElectricalMedium_ID
    -> AttributeCreator_5
    -> AttributeCreator_9
    -> AttributeCreator_24

Bookmark: Create Cables, FeatureGraphs, InteriorFeatureLinks and ExteriorMaterials
FeatureMerger
    MERGE_TYPE = Attributes Only
    ATTR_CONFLICT_RES = Use Requestor
    REJECT_NULL_MISSING_KEYS = No
    PROCESS_DUPS = No
    SUPPLIERS_FIRST = No
    ATTR_ACCUM_MODE = Merge Supplier
    IGNORE_NULLS = No
    JOIN_KEYS = 1 1 AUTO
    MERGED -> ListExploder
GEOTIFF (reader GEOTIFF_1)
    -> SurfaceDraper [POINTS/LINES]
SurfaceDraper
    ADDZ_TYPE = Replace Z
    TOLERANCE = -2
    DRAPE_TYPE = VERTEX
    INTERPOLATION_TYPE = AUTO
    DRAPED_FEATURES -> Offsetter_2
Offsetter_2
    YOFF = 0
    MODE = Cartesian Coordinate
    XOFF = 0
    ZOFF = 10
    OFFSET -> UUIDGenerator
Note: Set relationship between RoundPipe / and Network (+component)
AttributeCreator
    ATTR_TABLE = SET_TO citygml_feature_role = component
    -> AttributeRenamer_14
AttributeRenamer_14
    ATTR_TABLE = RENAME_SET_DEFAULT FeatureGraph_ID > utility_topo_graph_xlink_href
    -> StringConcatenator_19
StringConcatenator_19
    PARM_LINE = #@Value(utility_topo_graph_xlink_href)
    ACTION = Overwrite Existing Attributes
    ATTRLIST = utility_topo_graph_xlink_href
    -> FeatureMerger_7 [REQUESTOR]
Note: Remove Geometry because it is / irrelevant for FeatureGraphs
GeometryRemover_5
    -> AttributeCreator_4
Note: Set relationship between FeatureGraph / and NetworkGraph (+featureGraphMember)
AttributeCreator_4
    ATTR_TABLE = SET_TO citygml_feature_role = featureGraphMember
    -> AttributeRenamer_4
Note: Set gml_id (FeatureGraph_ID) / and gml_parent_id (NetworkGraph_ID)
AttributeRenamer_4
    ATTR_TABLE:
      RENAME_SET_DEFAULT FeatureGraph_ID > gml_id
      RENAME_SET_DEFAULT NetworkGraph_ID > gml_parent_id
    -> FeatureGraph (writer CITYGML_2)
    -> FeatureMerger_15 [SUPPLIER]
Note: Set relationship between FeatureGraph / and InteriorFeatureLink (+linkMember)
AttributeCreator_6
    ATTR_TABLE = SET_TO citygml_feature_role = linkMember
    -> AttributeRenamer_8
Note: Set gml_id (InteriorFeatureLink ID) / Also set gml_parent_id (FeatureGraph)
AttributeRenamer_8
    ATTR_TABLE:
      RENAME_SET_DEFAULT InteriorFeatureLink_ID > gml_id
      RENAME_SET_DEFAULT FeatureGraph_ID > gml_parent_id
    -> StringConcatenator_22
StringConcatenator_22
    PARM_LINE = #@Value(utility_start_xlink_href)
    ACTION = Overwrite Existing Attributes
    ATTRLIST = utility_start_xlink_href
    -> StringConcatenator_21
StringConcatenator_21
    PARM_LINE = #@Value(utility_end_xlink_href)
    ACTION = Overwrite Existing Attributes
    ATTRLIST = utility_end_xlink_href
    -> InteriorFeatureLink (writer CITYGML_2)
    -> cable_interiorfeaturelink
cable_interiorfeaturelink: Inspector
Creator_2
    NUM = 1
    GEOMTYPE = Geometry Object
    CREATED -> UUIDGenerator_8
Note: Create attribute utility_type / and use the existing MATERIAL / attribute
AttributeCreator_10
    ATTR_TABLE = SET_TO utility_type = rubber
    -> AttributeRenamer_12
Note: Set gml_id as ExteriorMaterialID
AttributeRenamer_12
    ATTR_TABLE = RENAME_SET_DEFAULT ExteriorMaterial_ID > gml_id
    -> ExteriorMaterial (writer CITYGML_2)
Note: Map the ExteriorMaterial to the / Cables
FeatureMerger_7
    MERGE_TYPE = Attributes Only
    ATTR_CONFLICT_RES = Use Requestor
    REJECT_NULL_MISSING_KEYS = No
    PROCESS_DUPS = No
    SUPPLIERS_FIRST = No
    ATTR_ACCUM_MODE = Merge Supplier
    IGNORE_NULLS = No
    JOIN_KEYS = 1 1 AUTO
    MERGED -> AttributeRenamer_11
Note: Set relationship between RoundPipes / and ExteriorMaterials via Xlink
AttributeRenamer_11
    ATTR_TABLE:
      RENAME_SET_DEFAULT ExteriorMaterial_ID > utility_has_material{0}.xlink_href
      RENAME_SET_DEFAULT TYPE > utility_class
      RENAME_SET_DEFAULT YEAR > utility_year_of_construction
      RENAME_SET_DEFAULT ACCURACY > utility_location_quality
    -> StringConcatenator_20
StringConcatenator_20
    PARM_LINE = #@Value(utility_has_material{0}.xlink_href)
    ACTION = Overwrite Existing Attributes
    ATTRLIST = utility_has_material{0}.xlink_href
    -> FeatureMerger_15 [REQUESTOR]
FeatureMerger_15
    MERGE_TYPE = Attributes Only
    ATTR_CONFLICT_RES = Use Requestor
    REJECT_NULL_MISSING_KEYS = No
    PROCESS_DUPS = No
    SUPPLIERS_FIRST = No
    ATTR_ACCUM_MODE = Merge Supplier
    IGNORE_NULLS = No
    JOIN_KEYS = @Value(Cable_ID) @Value(Cable_ID) AUTO
    MERGED -> AttributeRenamer_5
Note: Set gml_id as RoundPipeID / and gml_parent_id as NetworkID
AttributeRenamer_5
    ATTR_TABLE:
      RENAME_SET_DEFAULT Network_ID > gml_parent_id
      RENAME_SET_DEFAULT Cable_ID > gml_id
    -> AttributeCreator_25
AttributeCreator_25
    ATTR_TABLE:
      SET_TO utility_function = distribution
      SET_TO utility_status = inUse
      SET_TO utility_function_of_line = flowLine
      SET_TO utility_location_quality = assumed
      SET_TO utility_elevation_quality = assumed
    -> Cable (writer CITYGML_2)
    -> Cable

Bookmark: Node IDs
Note: 1. Each node contains a list which lists all lines (i.e. the corresponding arc_ids) that are connected with the node. / This list is split up here so that each node is connected to one line only. / The number of nodes duplicates analogously to the number of lines connected with a node.
ListExploder
    INDEX_ATTR = _element_index
    ATTR_ACCUM_MODE = Merge Incoming List
    LIST_ATTR = _node_angle{}
    ATTR_CONFLICT_RES = Use Incoming List
    ELEMENTS -> ExpressionEvaluator
Note: Arc_ids with a negative sign are / turned into positive numbers here.
ExpressionEvaluator
    ACTION = Overwrite Existing Attributes
    EXPRESSION = @abs(@Value(fme_arc_id))
    ATTRLIST = fme_arc_id
    -> UUIDGenerator_6
FeatureMerger_5
    MERGE_TYPE = Attributes Only
    ATTR_CONFLICT_RES = Use Requestor
    REJECT_NULL_MISSING_KEYS = No
    PROCESS_DUPS = No
    SUPPLIERS_FIRST = No
    ATTR_ACCUM_MODE = Merge Supplier
    IGNORE_NULLS = No
    JOIN_KEYS = @Value(Node_ID) @Value(utility_start_xlink_href) AUTO
    MERGED -> AttributeCreator_11
    NOT_MERGED -> FeatureMerger_6 [REQUESTOR]
FeatureMerger_6
    MERGE_TYPE = Attributes Only
    ATTR_CONFLICT_RES = Use Requestor
    REJECT_NULL_MISSING_KEYS = No
    PROCESS_DUPS = No
    SUPPLIERS_FIRST = No
    ATTR_ACCUM_MODE = Merge Supplier
    IGNORE_NULLS = No
    JOIN_KEYS = @Value(Node_ID) @Value(utility_end_xlink_href) AUTO
    MERGED -> AttributeCreator_11
Note: Set type = exterior
AttributeCreator_11
    ATTR_TABLE = SET_TO utility_type = exterior
    -> 3DForcer_3
Note: Set relation between FeatureGraph / and Node (+nodeMember)
AttributeCreator_8
    ATTR_TABLE = SET_TO citygml_feature_role = nodeMember
    -> AttributeRenamer_9
Note: Set gml_id to Node_ID / and gml_parent_id to FeatureGraph_ID
AttributeRenamer_9
    ATTR_TABLE:
      RENAME_SET_DEFAULT Node_ID > gml_id
      RENAME_SET_DEFAULT FeatureGraph_ID > gml_parent_id
    -> Node (writer CITYGML_2)
    -> cable_node
cable_node: Inspector

Bookmark: Node ID
UUIDGenerator_6
    UUID_ATTR = Node_ID
    -> StringConcatenator_6
StringConcatenator_6
    PARM_LINE = NodeID_@Value(Node_ID)
    ACTION = Overwrite Existing Attributes
    ATTRLIST = Node_ID
    -> FeatureMerger_3 [SUPPLIER]
    -> FeatureMerger_4 [SUPPLIER]
    -> FeatureMerger_5 [REQUESTOR]
    -> AttributeRemover
    -> FeatureMerger_14 [REQUESTOR]
    -> FeatureMerger_14 [SUPPLIER]

Bookmark: InterFeatureLink ID
UUIDGenerator_14
    UUID_ATTR = InterFeatureLink_ID
    -> StringConcatenator_14
StringConcatenator_14
    PARM_LINE = InterFeatureLinkID_@Value(InterFeatureLink_ID)
    ACTION = Overwrite Existing Attributes
    ATTRLIST = InterFeatureLink_ID
    -> AttributeRenamer_24

Bookmark: Join with Nodes from Cables
AttributeRemover
    REMOVE_ATTRS = _node_number,Network_ID,NetworkGraph_ID,_creation_instance,_element_index,fme_arc_id,id,type,fme_arc_angle
    -> AttributeRenamer_13
AttributeRenamer_13
    ATTR_TABLE = RENAME_SET_DEFAULT Node_ID > Cable_NodeID
    -> SpatialRelator [Supplier]
SpatialRelator
    CALC_CARD = No
    CURVE_BOUNDARY_RULE_PARAM = Default Rule
    AGGREGATE_HANDLING = Yes
    ATTR_CONFLICT_RES = Use Requestor
    SUCCESS_ATTR = _related_candidates
    PREDICATES = INTERSECTS
    ATTR_ACCUM_MODE = Merge Supplier
    -> AttributeCreator_28
    -> AttributeCreator_29
    -> AttributeCreator_30

Bookmark: Prepare features to be written as TerminalElements
AttributeCreator_31
    ATTR_TABLE = SET_TO citygml_feature_role = component
    -> AttributeRenamer
AttributeRenamer
    ATTR_TABLE:
      RENAME_SET_DEFAULT ElectricalTerminalElementID > gml_id
      RENAME_SET_DEFAULT Network_ID > gml_parent_id
    -> AttributeRenamer_33
AttributeRenamer_33
    ATTR_TABLE = RENAME_SET_DEFAULT FeatureGraph_ID > utility_topo_graph_xlink_href
    -> StringConcatenator_27
StringConcatenator_27
    PARM_LINE = #@Value(utility_topo_graph_xlink_href)
    ACTION = Overwrite Existing Attributes
    ATTRLIST = utility_topo_graph_xlink_href
    -> AttributeCreator_32
AttributeCreator_32
    ATTR_TABLE:
      SET_TO utility_status = inUse
      SET_TO utility_location_quality = assumed
      SET_TO utility_elevation_quality = assumed
    -> TerminalElement (writer CITYGML_2)

Bookmark: TerminalElement FeatureGraphs
AttributeCreator_28
    ATTR_TABLE = SET_TO citygml_feature_role = featureGraphMember
    -> AttributeRenamer_20
AttributeRenamer_20
    ATTR_TABLE:
      RENAME_SET_DEFAULT FeatureGraph_ID > gml_id
      RENAME_SET_DEFAULT NetworkGraph_ID > gml_parent_id
    -> FeatureGraph (writer CITYGML_2)

Bookmark: TerminalElement Nodes
AttributeCreator_29
    ATTR_TABLE:
      SET_TO citygml_feature_role = nodeMember
      SET_TO utility_type = exterior
    -> AttributeRenamer_31
AttributeRenamer_31
    ATTR_TABLE:
      RENAME_SET_DEFAULT Node_ID > gml_id
      RENAME_SET_DEFAULT FeatureGraph_ID > gml_parent_id
    -> 3DForcer_6

Bookmark: Set CityGML Geometry
3DForcer_6
    ZVALATTR = 0
    KEEPZVAL = No
    -> AttributeCreator_26
AttributeCreator_26
    ATTR_TABLE = SET_TO citygml_lod_name = realization
    -> GeometryPropertySetter_7
GeometryPropertySetter_7
    SRC_ATTRS = citygml_lod_name
    OVERWRITE_CHOICE = Yes
    SETTYPE_PARAM = Traits From Attributes
    REMOVE_ATTRIBUTE = No
    SET -> Node (writer CITYGML_2)
    SET -> terminalelement_node

Bookmark: InterFeatureLinks from Cable Nodes to TerminalElement Nodes
AttributeCreator_30
    ATTR_TABLE = SET_TO citygml_feature_role = linkMember
    -> AttributeRenamer_32
AttributeRenamer_32
    ATTR_LIST = Node_ID,utility_start_xlink_href,,Cable_NodeID,utility_end_xlink_href,,InterFeatureLink_ID,gml_id,,NetworkGraph_ID,gml_parent_id,
    -> StringConcatenator_25
StringConcatenator_25
    PARM_LINE = #@Value(utility_start_xlink_href)
    ACTION = Overwrite Existing Attributes
    ATTRLIST = utility_start_xlink_href
    -> StringConcatenator_26
StringConcatenator_26
    PARM_LINE = #@Value(utility_end_xlink_href)
    ACTION = Overwrite Existing Attributes
    ATTRLIST = utility_end_xlink_href
    -> GeometryRemover_6
    -> InterFeatureLink (writer CITYGML_2)
    -> terminalelement_interfeaturelink
GeometryRemover_6 [off]
    -> InterFeatureLink (writer CITYGML_2)

Bookmark: Cable ID
UUIDGenerator
    UUID_ATTR = Cable_ID
    -> StringConcatenator
StringConcatenator
    PARM_LINE = CableID_@Value(Cable_ID)
    ACTION = Overwrite Existing Attributes
    ATTRLIST = Cable_ID
    -> UUIDGenerator_4

Bookmark: InteriorFeatureLink ID
UUIDGenerator_4
    UUID_ATTR = InteriorFeatureLink_ID
    -> StringConcatenator_4
StringConcatenator_4
    PARM_LINE = InteriorFeatureLinkID_@Value(InteriorFeatureLink_ID)
    ACTION = Overwrite Existing Attributes
    ATTRLIST = InteriorFeatureLink_ID
    -> UUIDGenerator_5

Bookmark: FeatureGraph ID
UUIDGenerator_5
    UUID_ATTR = FeatureGraph_ID
    -> StringConcatenator_5
StringConcatenator_5
    PARM_LINE = FeatureGraphID_@Value(FeatureGraph_ID)
    ACTION = Overwrite Existing Attributes
    ATTRLIST = FeatureGraph_ID
    -> GeometryRemover_5
    -> FeatureMerger_3 [REQUESTOR]
    -> Offsetter

Bookmark: Make features 3D and set CityGML geometry
Offsetter
    YOFF = 0
    MODE = Cartesian Coordinate
    XOFF = 0
    ZOFF = 110
    OFFSET -> AttributeCreator_2
AttributeCreator_2
    ATTR_TABLE:
      SET_TO citygml_lod_name = lod1Geometry
      SET_TO utility_has_material{0}.xlink_href = hasMaterial
    -> GeometryPropertySetter
GeometryPropertySetter
    SRC_ATTRS = citygml_lod_name
    OVERWRITE_CHOICE = Yes
    SETTYPE_PARAM = Traits From Attributes
    REMOVE_ATTRIBUTE = No
    SET -> AttributeCreator

Bookmark: Connect InteriorFeatureLinks with Nodes
Note: Connect InteriorFeatureLinks with Nodes. / Now InteriorFeatureLinks have attributes of Nodes / So InteriorFeatureLinks can have a reference to a start Node
FeatureMerger_3
    MERGE_TYPE = Attributes Only
    ATTR_CONFLICT_RES = Use Requestor
    REJECT_NULL_MISSING_KEYS = No
    PROCESS_DUPS = No
    SUPPLIERS_FIRST = No
    ATTR_ACCUM_MODE = Merge Supplier
    IGNORE_NULLS = No
    JOIN_KEYS = @Value(_edge_id) @Value(fme_arc_id) AUTO @Value(_from_node) @Value(_node_number) AUTO
    MERGED -> AttributeRenamer_6
Note: Set XLink reference between / InteriorFeatureLink and start / nodes
AttributeRenamer_6
    ATTR_TABLE = RENAME_SET_DEFAULT Node_ID > utility_start_xlink_href
    -> FeatureMerger_4 [REQUESTOR]
Note: Connect InteriorFeatureLinks with Nodes. / Now InteriorFeatureLinks have attributes of Nodes / So InteriorFeatureLinks can have a reference to a end Node
FeatureMerger_4
    MERGE_TYPE = Attributes Only
    ATTR_CONFLICT_RES = Use Requestor
    REJECT_NULL_MISSING_KEYS = No
    PROCESS_DUPS = No
    SUPPLIERS_FIRST = No
    ATTR_ACCUM_MODE = Merge Supplier
    IGNORE_NULLS = No
    JOIN_KEYS = @Value(_edge_id) @Value(fme_arc_id) AUTO @Value(_to_node) @Value(_node_number) AUTO
    MERGED -> AttributeRenamer_7
Note: Set XLink reference between / InteriorFeatureLink and end / nodes
AttributeRenamer_7
    ATTR_TABLE = RENAME_SET_DEFAULT Node_ID > utility_end_xlink_href
    -> 3DForcer_2
    -> FeatureMerger_5 [SUPPLIER]
    -> FeatureMerger_6 [SUPPLIER]

Bookmark: Set CityGML Geometry
3DForcer_2
    ZVALATTR = 0
    KEEPZVAL = No
    -> AttributeCreator_3
AttributeCreator_3
    ATTR_TABLE = SET_TO citygml_lod_name = realization
    -> GeometryPropertySetter_2
GeometryPropertySetter_2
    SRC_ATTRS = citygml_lod_name
    OVERWRITE_CHOICE = Yes
    SETTYPE_PARAM = Traits From Attributes
    REMOVE_ATTRIBUTE = No
    SET -> AttributeCreator_6

Bookmark: Set CityGML Geometry
3DForcer_3
    ZVALATTR = 0
    KEEPZVAL = No
    -> AttributeCreator_7
AttributeCreator_7
    ATTR_TABLE = SET_TO citygml_lod_name = realization
    -> GeometryPropertySetter_3
GeometryPropertySetter_3
    SRC_ATTRS = citygml_lod_name
    OVERWRITE_CHOICE = Yes
    SETTYPE_PARAM = Traits From Attributes
    REMOVE_ATTRIBUTE = No
    SET -> AttributeCreator_8

Bookmark: ExteriorMaterial ID
UUIDGenerator_8
    UUID_ATTR = ExteriorMaterial_ID
    -> StringConcatenator_8
StringConcatenator_8
    PARM_LINE = ExteriorMaterialID_@Value(ExteriorMaterial_ID)
    ACTION = Overwrite Existing Attributes
    ATTRLIST = ExteriorMaterial_ID
    -> FeatureMerger_7 [SUPPLIER]
    -> AttributeCreator_10

Bookmark: Direct carryovers from the water network
LiquidMedium (reader CITYGML_1)
    attributes: citygml_target_uri xml_buffer, citygml_feature_role xml_buffer, citygml_feature_role_attr_name xml_buffer, citygml_feature_role_attr_val xml_buffer, gml_description xml_buffer, gml_name xml_buffer, utility_owner xml_buffer, utility_is_classified_by{}.xlink_href xml_buffer, utility_associated_network{}.xlink_href xml_buffer, utility_type xml_buffer, utility_type_codeSpace xml_buffer, utility_is_corrosive xml_boolean, utility_is_explosive xml_boolean, utility_flammable xml_real64, utility_electric_conductivity xml_buffer, utility_electric_conductivity_units xml_buffer, utility_ph_value_range xml_buffer, utility_ph_value_range_units xml_buffer, utility_temperature_range xml_buffer, utility_temperature_range_units xml_buffer, utility_flow_rate_range xml_buffer, utility_flow_rate_range_units xml_buffer, utility_pressure_range xml_buffer, utility_pressure_range_units xml_buffer
    -> LiquidMedium (writer CITYGML_2)
LiquidMedium (writer CITYGML_2)
    attributes: citygml_target_uri xml_buffer, citygml_feature_role xml_buffer, citygml_feature_role_attr_name xml_buffer, citygml_feature_role_attr_val xml_buffer, gml_description xml_buffer, gml_name xml_buffer, utility_owner xml_buffer, utility_is_classified_by{}.xlink_href xml_buffer, utility_associated_network{}.xlink_href xml_buffer, utility_type xml_buffer, utility_type_codeSpace xml_buffer, utility_is_corrosive xml_boolean, utility_is_explosive xml_boolean, utility_flammable xml_real64, utility_electric_conductivity xml_buffer, utility_electric_conductivity_units xml_buffer, utility_ph_value_range xml_buffer, utility_ph_value_range_units xml_buffer, utility_temperature_range xml_buffer, utility_temperature_range_units xml_buffer, utility_flow_rate_range xml_buffer, utility_flow_rate_range_units xml_buffer, utility_pressure_range xml_buffer, utility_pressure_range_units xml_buffer
CityModel (reader CITYGML_1)
    attributes: citygml_target_uri xml_buffer, gml_description xml_buffer, gml_name xml_buffer, citygml_appearance_member{}.xlink_href xml_buffer, citygml_city_object_member{}.xlink_href xml_buffer, gml_feature_member{}.xlink_href xml_buffer
    -> CityModel (writer CITYGML_2)
CityModel (writer CITYGML_2)
    attributes: citygml_target_uri xml_buffer, gml_description xml_buffer, gml_name xml_buffer, citygml_city_object_member{}.xlink_href xml_buffer, citygml_appearance_member{}.xlink_href xml_buffer, gml_feature_member{}.xlink_href xml_buffer
RoundPipe (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64,
      utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer,
      utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer, utility_function_of_line xml_buffer, utility_function_of_line_codeSpace xml_buffer, utility_is_gravity xml_boolean, utility_exterior_width xml_real64, utility_exterior_width_units xml_buffer, utility_exterior_height xml_real64, utility_exterior_height_units xml_buffer, utility_exterior_diameter xml_real64, utility_exterior_diameter_units xml_buffer, utility_interior_diameter xml_real64, utility_interior_diameter_units xml_buffer
    -> RoundPipe (writer CITYGML_2)
    -> RoundPipe
RoundPipe (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer,
      utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer,
      utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer, utility_function_of_line xml_buffer, utility_function_of_line_codeSpace xml_buffer, utility_is_gravity xml_boolean, utility_exterior_width xml_real64, utility_exterior_width_units xml_buffer, utility_exterior_height xml_real64, utility_exterior_height_units xml_buffer, utility_exterior_diameter xml_real64, utility_exterior_diameter_units xml_buffer, utility_interior_diameter xml_real64, utility_interior_diameter_units xml_buffer
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64,
      utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer,
      utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, citygml_class xml_buffer, citygml_class_codeSpace xml_buffer, citygml_function{} xml_buffer, citygml_function{}.codeSpace xml_buffer, citygml_usage{} xml_buffer, citygml_usage{}.codeSpace xml_buffer,
      citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, utility_building_habitants{} xml_int64
    -> Building (writer CITYGML_2)
    -> Building
Building (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer,
      utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer,
      utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, citygml_class xml_buffer, citygml_class_codeSpace xml_buffer, citygml_function{} xml_buffer, citygml_function{}.codeSpace xml_buffer, citygml_usage{} xml_buffer, citygml_usage{}.codeSpace xml_buffer,
      citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, utility_building_habitants{} xml_int64
StorageDevice (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64,
      utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer,
      utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_description xml_buffer, utility_class xml_buffer, utility_class_codeSpace xml_buffer
    -> StorageDevice (writer CITYGML_2)
StorageDevice (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer,
      utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer,
      utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_description xml_buffer, utility_class xml_buffer, utility_class_codeSpace xml_buffer
ControllerDevice (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64,
      utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer,
      utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_description xml_buffer, utility_class xml_buffer, utility_class_codeSpace xml_buffer
    -> ControllerDevice (writer CITYGML_2)
ControllerDevice (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer,
      utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer,
      utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_description xml_buffer, utility_class xml_buffer, utility_class_codeSpace xml_buffer
SimpleFunctionalElement (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64,
      utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer,
      utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer
    -> SimpleFunctionalElement (writer CITYGML_2)
SimpleFunctionalElement (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29),
      utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer,
      utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer,
      utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer

FME custom transformer SmartCleaner_2013
SmartCleaner adds two new capabilities to the Intersector - extending undershot lines to intersection and deleting overshoots shorter than a specified length. 
Both the undershoot and overshoot tolerances may be taken from a feature attribute or a keyin. This transformer works only on lines, all other features are sent to the <REJECTED> port.
See http://knowledge.safe.com/articles/How_To/Example-of-the-SmartCleaner-Custom-Transformer for more information.
The transformer has two parameters:
    Extension Length:
The distance to extend undershot lines in order to intersect another line.
    Overshoot Length:
The minimum length a dangling line must be in order to be retained.

Parameters:
- LEN = 1   # Extension Length
- VAL = 1   # Overshoot Length

INPUT (input)
    -> GeometryFilter
Note: Route any non-line features / to rejected port
GeometryFilter
    BREAK_AGG = No
    POINT -> <REJECTED> (output)
    LINE -> GeometryValidator
    ARC -> <REJECTED> (output)
    AREA -> <REJECTED> (output)
    ELLIPSE -> <REJECTED> (output)
    TEXT -> <REJECTED> (output)
    RASTER -> <REJECTED> (output)
    POINTCLOUD -> <REJECTED> (output)
    SURFACE -> <REJECTED> (output)
    SOLID -> <REJECTED> (output)
    COLLECTION -> <REJECTED> (output)
    NULL -> <REJECTED> (output)
    INSTANCE -> <REJECTED> (output)
Note: Fix geometry problems
GeometryValidator
    DUP_COORDS_CHECK_Z = No
    OGC_SIMPLE_CHECK = OGC_SIMPLE_CHECK
    PLANAR_SURFACE = PLANAR_SURFACE
    PLANAR_TOLERANCE_MODE = Auto
    CHECK_HOLE_TOUCHING_POLYGON = No
    MISSING_TEXTURE_COORDINATES = MISSING_TEXTURE_COORDINATES
    PRESETS = All
    SELF_INTERSECTING = SELF_INTERSECTING
    MISSING_VERTEX_NORMALS = MISSING_VERTEX_NORMALS
    SHELL_VALIDATION = SHELL_VALIDATION
    CONSECUTIVE_IDENTICAL_VERTICES_2D = CONSECUTIVE_IDENTICAL_VERTICES_2D
    OGC_VALID_CHECK = OGC_VALID_CHECK
    TYPE_REPAIR = TYPE_REPAIR
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%MISSING_VERTEX_NORMALS%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"
    NAN_REMOVAL = NAN_REMOVAL
    REPAIR = Yes
    SOLID_VOID_REPAIR = SOLID_VOID_REPAIR
    NULL_REMOVAL = NULL_REMOVAL
    PASSED -> Intersector
    FAILED -> Intersector
    REPAIRED -> Intersector
Note: Intersect lines
Intersector
    SEG_ATTR = _segments
    SEPARATE_COLLINEAR_SEGMENTS = No
    PERFORM_SELF_INTERSECTION = No
    DUPLICATE_Z_NODES = No
    OV_ATTR = _overlaps
    INTERSECTED -> TopologyBuilder [LINE]
Note: Create node/line / topology to query
TopologyBuilder
    OVERLAPPING_MODE = No
    MAX = 0
    ALL_EDGES = Yes
    CLEAN_DATA = Yes
    PROP_ATTRS = No
    ALLOW_CYCLES = No
    LINE -> Cloner
    LINE -> TestFilter_2
Note: Find dangling lines to extend
TestFilter_2
    DEFAULT_VALUE = <UNFILTERED>
    TEST_LIST:
      BOOL_OP,AND,COMPOSITE_TEST,<Unused>,TEST_CLAUSE,"TEST @Evaluate(abs(@Value(_right_edge))) = @Value(_arc_id)
      TEST @Evaluate(abs(@Value(_left_edge))) = @Value(_arc_id)",BOTH,BOOL_OP,AND,COMPOSITE_TEST,<Unused>,TEST_CLAUSE,"TEST @Evaluate(abs(@Value(_left_edge))) = @Value(_arc_id)",BEGINNING,BOOL_OP,AND,COMPOSITE_TEST,<Unused>,TEST_CLAUSE,"TEST @Evaluate(abs(@Value(_right_edge))) = @Value(_arc_id)",END
    BOTH -> Extender
    BOTH -> Extender_2
    BEGINNING -> Extender
    END -> Extender_2
Note: Attached to other lines only / at the end, so extend start / of line
Extender
    LEN = $(LEN)
    NUM_SEGS = 1
    BEGINNING -> AttributeCreator_2
Note: Attached to other lines only / at the start, so extend end / of line
Extender_2
    LEN = $(LEN)
    NUM_SEGS = 1
    END -> AttributeCreator_2
Note: Flag extensions for / future cleanup
AttributeCreator_2
    ATTR_LIST = _smartcleaner_extended,1
    -> AttributeRemover_3
Note: Attached at both / ends, so no extension
Cloner
    COPYATT = _copynum
    COPIES = 1
    COPY -> AttributeRemover_3
Note: Clean up unneeded / attributes
AttributeRemover_3
    REMOVE_ATTRS = _overlaps,_segments,_arc_id,_right_polygon,_left_polygon,_right_edge,_left_edge,_from_node,_to_node,_polygons,_copynum
    -> GeometryValidator_2
Note: Fix geometry problems
GeometryValidator_2
    DUP_COORDS_CHECK_Z = No
    OGC_SIMPLE_CHECK = OGC_SIMPLE_CHECK
    PLANAR_SURFACE = PLANAR_SURFACE
    PLANAR_TOLERANCE_MODE = Auto
    CHECK_HOLE_TOUCHING_POLYGON = No
    MISSING_TEXTURE_COORDINATES = MISSING_TEXTURE_COORDINATES
    PRESETS = All
    SELF_INTERSECTING = SELF_INTERSECTING
    MISSING_VERTEX_NORMALS = MISSING_VERTEX_NORMALS
    SHELL_VALIDATION = SHELL_VALIDATION
    CONSECUTIVE_IDENTICAL_VERTICES_2D = CONSECUTIVE_IDENTICAL_VERTICES_2D
    OGC_VALID_CHECK = OGC_VALID_CHECK
    TYPE_REPAIR = TYPE_REPAIR
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%MISSING_VERTEX_NORMALS%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"
    NAN_REMOVAL = NAN_REMOVAL
    REPAIR = Yes
    SOLID_VOID_REPAIR = SOLID_VOID_REPAIR
    NULL_REMOVAL = NULL_REMOVAL
    PASSED -> Intersector_2
    FAILED -> Intersector_2
    REPAIRED -> Intersector_2
Note: Intersect lines and extensions
Intersector_2
    SEG_ATTR = _segments
    SEPARATE_COLLINEAR_SEGMENTS = No
    PERFORM_SELF_INTERSECTION = No
    DUPLICATE_Z_NODES = No
    OV_ATTR = _overlaps
    INTERSECTED -> TopologyBuilder_2 [LINE]
Note: Recreate query topology
TopologyBuilder_2
    OVERLAPPING_MODE = No
    MAX = 0
    ALL_EDGES = Yes
    CLEAN_DATA = Yes
    PROP_ATTRS = No
    ALLOW_CYCLES = No
    LINE -> Tester
Note: Remove extended dangles
Tester
    BOOL_OP = COMPOSITE
    TEST_DESCRIPTION = ""
    TEST_CLAUSE:
      TEST @Evaluate(abs(@Value(_left_edge))) = @Value(_arc_id)
      TEST @Evaluate(abs(@Value(_right_edge))) = @Value(_arc_id)
      TEST @Value(_smartcleaner_extended) = 1
    TEST_MODE = Automatic
    COMPOSITE_TEST = "(1 OR 2) AND 3"
    FAILED -> AttributeRemover
Note: Clean up attributes
AttributeRemover
    REMOVE_ATTRS = _overlaps,_segments,_arc_id,_right_polygon,_left_polygon,_right_edge,_left_edge,_from_node,_to_node,_polygons
    -> TopologyBuilder_3 [LINE]
Note: Recreate query topology / with extensions removed
TopologyBuilder_3
    OVERLAPPING_MODE = No
    MAX = 0
    ALL_EDGES = Yes
    CLEAN_DATA = Yes
    PROP_ATTRS = No
    ALLOW_CYCLES = No
    LINE -> LengthCalculator
Note: Calculate line length
LengthCalculator
    DIM = 2
    MULT = 1
    LEN_ATTR = _length
    -> Tester_2
Note: Remove any dangling / lines less than Overshoot / Length
Tester_2
    BOOL_OP = COMPOSITE
    TEST_DESCRIPTION = ""
    TEST_CLAUSE:
      TEST @Evaluate(abs(@Value(_left_edge))) = @Value(_arc_id)
      TEST @Evaluate(abs(@Value(_right_edge))) = @Value(_arc_id)
      TEST @Value(_length) < $(VAL)
    TEST_MODE = Automatic
    COMPOSITE_TEST = "(1 OR 2) AND 3"
    FAILED -> AttributeRemover_2
Note: Clean up attributes
AttributeRemover_2
    REMOVE_ATTRS = _smartcleaner_extended,_arc_id,_right_polygon,_left_polygon,_right_edge,_left_edge,_from_node,_to_node,_polygons,_length
    -> CLEANED (output)
CLEANED (output)
<REJECTED> (output)
